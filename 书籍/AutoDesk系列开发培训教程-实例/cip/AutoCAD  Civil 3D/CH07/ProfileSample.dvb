Attribute VB_Name = "BaseObjects"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' 声明全局的程序、文档和数据库对象
Public g_oCivilApp As AeccApplication
Public g_oDocument As AeccDocument
Public g_oAeccDb As AeccDatabase


''---------------------------------------------------------
'
'功能：获取模块的程序、文档和数据库对象
'
'作者：
'
'
'日期：２００７/０8
'
'
'修改记录：无
'
'
''-----------------------------------------------------------
Public Function GetBaseCivilObjects() As Boolean
    Dim oApp As AcadApplication
    Set oApp = ThisDrawing.Application
    '需要指定版本号（5.0）.
    Const sAppName = "AeccXUiLand.AeccApplication.5.0"
    Set g_oCivilApp = oApp.GetInterfaceObject(sAppName)
    If g_oCivilApp Is Nothing Then
        MsgBox "获取程序对象 " & sAppName & "错误, 退出."
        GetBaseCivilObjects = False
        Exit Function
    End If
    Set g_oDocument = g_oCivilApp.ActiveDocument
    Set g_oAeccDb = g_oDocument.Database
    GetBaseCivilObjects = True
End Function

Attribute VB_Name = "Profile"
'
' MODULE_ID {Profile.bas}
' {ProfileSample.dvb}
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'
' Create a profile based on the surface named SURFACE_NAME and
' the alignment
'

'''---------------------------------------------------------
'
'功能：基于路线和曲面创建纵断面
'
'作者：
'
'
'日期：２００７/０8
'
'
'修改记录：无
'
'
''-----------------------------------------------------------
Public Function CreateProfile(oAlignment As AeccAlignment) As Boolean
    ' 判断数据库对象是否有效
    If (g_oAeccDb Is Nothing) Then
        CreateProfile = False
        Exit Function
    End If
    
    ' 获取特定曲面
    Dim oSurface As AeccSurface
    On Error Resume Next
    Set oSurface = g_oAeccDb.Surfaces.Item(0)
    If (oSurface Is Nothing) Then
        Debug.Print "曲面不存在."
        CreateProfile = False
        Exit Function
    End If

    ' 获取路线的纵断面集合
    Dim oProfiles As AeccProfiles
    On Error Resume Next
    Set oProfiles = oAlignment.Profiles
    On Error GoTo 0
    If (oProfiles Is Nothing) Then
        Debug.Print "获取路线的纵断面集合失败"
        CreateProfile = False
        Exit Function
    End If

    ' 创建纵断面样式.
    Dim oProfileStyle As AeccProfileStyle
    If (CreateProfileStyle("profile style 01") = False) Then
        MsgBox "Error creating profile style."
        CreateProfile = False
        Exit Function
    End If
    Set oProfileStyle = g_oDocument.LandProfileStyles.Item("profile style 01")

    ' 基于路线和曲面创建纵断面
    On Error Resume Next
    Dim oProfile As AeccProfile
    Set oProfile = oProfiles.Item("PROFILE_01")
    On Error GoTo 0
    If (oProfile Is Nothing) Then
        Set oProfile = oProfiles.AddFromSurface("PROFILE_01", aeccExistingGround, oProfileStyle, oSurface.Name, oAlignment.StartingStation, oAlignment.EndingStation, "0")
        oProfile.Update
        If oProfile Is Nothing Then
            Debug.Print "基于路线和曲面创建纵断面失败"
            CreateProfile = False
            Exit Function
        End If
    End If
    oProfile.ShowLabels = True
    oProfile.Style.LineDisplayStyle2d.color = acRed


    '基于同样的路线创建基于实体的第二个纵断面
    Set oProfile = Nothing
    On Error Resume Next
    Set oProfile = oProfiles.Item("PROFILE_02")
    On Error GoTo 0
    If (oProfile Is Nothing) Then
        Set oProfile = oProfiles.Add("PROFILE_02", aeccFinishedGround, oProfileStyle.Name, oAlignment.StartingStation, oAlignment.EndingStation, "0")
        '添加定义纵断面的实体
        Dim dLoc1(0 To 1) As Double
        Dim dLoc2(0 To 1) As Double
        Dim oProfileTangent1 As aeccProfileTangent
        dLoc1(0) = oAlignment.StartingStation: dLoc1(1) = -40#
        dLoc2(0) = 758.2: dLoc2(1) = -70#
        Set oProfileTangent1 = oProfile.Entities.AddFixedTangent(dLoc1, dLoc2)
        Dim oProfileTangent2 As aeccProfileTangent
        dLoc1(0) = 1508.2: dLoc1(1) = -60#
        dLoc2(0) = oAlignment.EndingStation: dLoc2(1) = -4#
        Set oProfileTangent2 = oProfile.Entities.AddFixedTangent(dLoc1, dLoc2)
        
        Dim dCrestLen As Double
        dCrestLen = 900.1
        Call oProfile.Entities.AddFreeSymmetricParabolaByLength(oProfileTangent1.Id, oProfileTangent2.Id, aeccSag, dCrestLen, True)
        
        ' 输出相关信息
        Debug.Print "PVI 数目: "; oProfile.PVIs.Count
        Dim oPVI As AeccProfilePVI
        For Each oPVI In oProfile.PVIs
            Debug.Print "PVI  里程:   "; oPVI.Station
            Debug.Print "     高程: "; oPVI.Elevation
            Debug.Print
        Next
        
        ' 查找靠近里程1000，高程-70的PVI.
        Set oPVI = Nothing
        Set oPVI = oProfile.PVIs.ItemAt(1000, -70)
        Debug.Print "靠近里程1000，高程-70的PVI在里程: "; oPVI.Station
        
        ' 添加另外一个 PVI ，需要调整一下其高程.
        Set oPVI = oProfile.PVIs.Add(607.4, -64.3, aeccProfileTangent)
        oPVI.Elevation = oPVI.Elevation - 2#
        oProfile.Update
    End If
    oProfile.ShowLabels = True
    oProfile.Style.LineDisplayStyle2d.color = acRed
    
    oProfile.Update
    CreateProfile = True
End Function

Attribute VB_Name = "ProfileStyle"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'''---------------------------------------------------------
'
'功能：创建纵断面样式
'
'作者：
'
'
'日期：２００７/０8
'
'
'修改记录：无
'
'
''-----------------------------------------------------------
Public Function CreateProfileStyle(sStyleName As String) As Boolean
    ' Delete the style if it already exists.
    On Error Resume Next
    g_oDocument.ProfileStyles.Remove sStyleName
    On Error GoTo 0
    
    ' Create a new style and add it to the drawing's collection
    ' of profile styles.
    Dim oProfileStyle As AeccProfileStyle
    On Error Resume Next
    Set oProfileStyle = g_oDocument.LandProfileStyles.Add("profile style 01")
    On Error GoTo 0
    If (oProfileStyle Is Nothing) Then
        On Error Resume Next
        Set oProfileStyle = g_oDocument.LandProfileStyles.Item("profile style 01")
        On Error GoTo 0
        If (oProfileStyle Is Nothing) Then
            MsgBox "Error creating profile style."
            CreateProfileStyle = False
            Exit Function
        End If
    End If
    
    ' Now set the style.
    oProfileStyle.ArrowDisplayStyle2d.color = 140 ' orange
    oProfileStyle.ArrowDisplayStyle2d.LinetypeScale = 200
    oProfileStyle.ArrowDisplayStyle2d.Visible = True
    
    oProfileStyle.AsymmetricalParabolaDisplayStyle2d.color = 140 ' slate
    oProfileStyle.CurveDisplayStyle2d.color = 190 ' purple
    oProfileStyle.LineDisplayStyle2d.color = 210 ' pink
    oProfileStyle.LineExtensionDisplayStyle2d.color = 50 ' yellow
    oProfileStyle.ParabolicCurveExtensionDisplayStyle2d.color = 130 ' light blue
    oProfileStyle.SymmetricalParabolaDisplayStyle2d.color = 110 ' turq
    
    CreateProfileStyle = True
End Function

Attribute VB_Name = "ProfileView"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'''---------------------------------------------------------
'
'功能：创建纵断面图
'
'作者：
'
'
'日期：２００７/０8
'
'
'修改记录：无
'
'
''-----------------------------------------------------------

Public Function CreateProfileView(oAlignment As AeccAlignment) As Boolean
    ' 设置纵断面图的插入原点
    Dim dOriginPt(0 To 2) As Double
    dOriginPt(0) = 6500#  ' to the right of the surface
    dOriginPt(1) = 4200#  ' slightly higher than the surface

    ' 创建纵断面图样式
    Dim oPVStyle As AeccProfileViewStyle
    If (CreateProfileViewStyle("PROFILE_VIEW_STYLE01") = False) Then
        MsgBox "创建纵断面图样式失败."
        CreateProfileView = False
        Exit Function
    End If
    Set oPVStyle = g_oDocument.ProfileViewStyles.Item("PROFILE_VIEW_STYLE01")

    ' 创建纵断面图标注栏集
    Dim oPVBandStyleSet As AeccProfileViewBandStyleSet
    If (CreateBandStyleSet("PROFILEVIEW_BAND_STYLE_01") = False) Then
        Debug.Print "创建纵断面图标注栏集失败"
        CreateProfileView = False
        Exit Function
    End If
    Set oPVBandStyleSet = g_oDocument.ProfileViewBandStyleSets.Item("PROFILEVIEW_BAND_STYLE_01")

    ' 创建纵断面图.
    Dim oProfileView As AeccProfileView
    On Error Resume Next
    Set oProfileView = oAlignment.ProfileViews.Item("PROFILE_VIEW_01")
    On Error GoTo 0
    If oProfileView Is Nothing Then
        Set oProfileView = oAlignment.ProfileViews.Add("PROFILE_VIEW_01", "0", dOriginPt, oPVStyle, oPVBandStyleSet)
    End If
    oProfileView.Description = "纵断面图基于路线‘" & oAlignment.Name & "’创建"
    oProfileView.Style = g_oDocument.ProfileViewStyles.Item(0)
    
    CreateProfileView = True
End Function

Attribute VB_Name = "ProfileViewStyle"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'


'''---------------------------------------------------------
'
'功能：创建纵断面图样式
'
'作者：
'
'
'日期：２００７/０8
'
'
'修改记录：无
'
'
''-----------------------------------------------------------
'
Function CreateProfileViewStyle(sStyleName As String) As Boolean
    ' First we check to see if a style with this name already exists.
    ' If so we will erase it.
    Dim oProfileViewStyle As AeccProfileViewStyle
    On Error Resume Next
    Set oProfileViewStyle = g_oDocument.ProfileViewStyles.Item(sStyleName)
    On Error GoTo 0
    If (Not oProfileViewStyle Is Nothing) Then
        ' If it is in use, it cannot be removed and will error
        ' on any attempt to do so.  We will catch the errors
        ' and do nothing if one takes place.
        On Error Resume Next
        g_oDocument.ProfileViewStyles.Remove sStyleName
        On Error GoTo 0
    End If

    ' Make a new profile view style and attach it to the
    ' drawing's collection of profile view styles.
    On Error Resume Next
    Set oProfileViewStyle = g_oDocument.ProfileViewStyles.Add(sStyleName)
    On Error GoTo 0
    If (oProfileViewStyle Is Nothing) Then
        CreateProfileViewStyle = False
        Exit Function
    End If
    ' This style automatically has the features of the standard
    ' profile view style for the drawing.
    
    '' Some information:
    '' Vertical lines in the graph are based on the bottom axis
    '' interval.  Top axis intervals only matter for how the
    '' tick marks are placed along the top axis.
    
    ' We will first adjust how the bottom axis is displayed.
    ' This involves setting the properties of a number of
    ' subobjects, each of which describes how a feature of the
    ' bottom axis is displayed.
    
    ' First, adjust the bottom axis.  We will put station
    ' information here, with the title at the far left.
    With oProfileViewStyle.BottomAxis
        .DisplaySyle2d.color = 60
        .DisplaySyle2d.Visible = True
        .MajorTickStyle.Size = 0.01
        ' NOTE: See Chapter 54 (Sections Dialog Boxes) for
        ' information about the name template.
        .MajorTickStyle.Text = "<[Station Value(Uft|FS|P2|RN|Sn|OF|AP|B2|TP|EN|W0|DZY)]>"
        .MajorTickStyle.Interval = 50 ' feet, in documents that use Imperial measures
        Dim dPoint(0 To 2) As Double
        dPoint(0) = -0.13
        dPoint(1) = 0#
        .TitleStyle.Offset = dPoint
        .TitleStyle.Text = "Stations"
        .TitleStyle.Position = aeccStart
    End With

    ' Now the top axis.  We will use this to mark meters
    ' from the start of the profile at an interval that
    ' is markedly different than the bottom axis.
    '
    ' Linetype lets you select among the types of lines loaded
    ' into the drawing or from .lin files.
    With oProfileViewStyle.TopAxis
        .DisplaySyle2d.Visible = True
        ' We will modify the text to display yards in decimal
        ' format, instead of the more usual feet in station format.
        .MajorTickStyle.Text = "<[Station Value(Um|FD|P1|RN|Sn|OF|AP|B2|TP|EN|W0|DZY)]> meters"
        .MajorTickStyle.Interval = 164.041995  ' 50 meters, in feet
        .TitleStyle.Text = "Meters"
        .TitleStyle.Position = aeccStart
    End With

    ' Now the properties of the graph.
    With oProfileViewStyle.GraphStyle
        .TitleStyle.Text = "Profile View of:<[Parent Alignment(CP)]>"
        .VerticalExaggeration = 5
        .Direction = aeccLeftToRight
        .GridStyle.GridsAboveMaxElevation = 1
        .GridStyle.GridsBelowDatum = 1
    End With

    ' And the properties of the lines of the graph that are
    ' drawn at each geometric change in the profile.
    With oProfileViewStyle.GridAtHGPDisplayStyle2d
        Dim oTrueColor As New AcadAcCmColor
        oTrueColor.SetRGB 5, 15, 254
        Set .TrueColor = oTrueColor
        .Linetype = "DOT"
        .Visible = True
    End With

    CreateProfileViewStyle = True
End Function ' CreateProfileViewStyle



'''---------------------------------------------------------
'
'功能：创建纵断面标签样式集
'
'作者：
'
'
'日期：２００７/０8
'
'
'修改记录：无
'
'
''-----------------------------------------------------------
'
Public Function CreateProfileLabelStyleSet(sStyleName As String) As Boolean
    Dim i As Integer
    
    ' Add a new AeccAlignmentLabelStyleSet in the document's
    ' collection of AlignmentStyleSet objects, after first
    ' deleting any older version of the style set that might
    ' exist.
    Dim oProfileLabelStyleSet As AeccProfileLabelStyleSet
    Set oProfileLabelStyleSet = Nothing
    On Error Resume Next
    g_oDocument.ProfileLabelStyleSets.Remove (sStyleName)
    On Error GoTo 0
    Set oProfileLabelStyleSet = g_oDocument.ProfileLabelStyleSets.Add(sStyleName)
    If (oProfileLabelStyleSet Is Nothing) Then
        Debug.Print "Error setting a Profile Label Style Set: " & Err.Description
        Err.Clear
        CreateProfileLabelStyleSet = vbNullString
        Exit Function
    End If
    ' Assign some profile label styles.
    oProfileLabelStyleSet.Description = "This is an overly complicated style set used as a demonstration."

    Dim oCrestCurveStyle As AeccLabelStyleSetItem
    Dim oLabelStyle As AeccLabelStyle
    Dim oLabelStyleTickComponent As AeccLabelStyleTickComponent
    Dim oLabelStyleLineComponent As AeccLabelStyleLineComponent
    Dim oLabelStyleTextComponent As AeccLabelStyleTextComponent
    Dim oLabelStyleBlockComponent As AeccLabelStyleBlockComponent
    
    ' -------------------------------------------------------
    ' This section demonstrates how to set the crest curve
    ' label style.  Sag curve and geometry point labels are
    ' similarly structured.

    ' Create a new label style for our crest curves and
    ' add it to the drawing's collection of profile label
    ' styles.
    On Error Resume Next
    g_oDocument.ProfileLabelStyles.CurveLabelStyles.Remove CREST_LABEL_STYLE_SET
    Set oLabelStyle = g_oDocument.ProfileLabelStyles.CurveLabelStyles.Item(CREST_LABEL_STYLE_SET)
    On Error GoTo 0
    If (oLabelStyle Is Nothing) Then
        Set oLabelStyle = g_oDocument.ProfileLabelStyles.CurveLabelStyles.Add(CREST_LABEL_STYLE_SET)
    End If

    ' Add to the AeccLabelStyle object an object for managing
    ' the style of label ticks.  This style governs the
    ' properties of the tick mark placed at regular intervals
    ' (in this case, at every station).
    On Error Resume Next
    oLabelStyle.TickComponents.Remove TICK_STYLE
    Set oLabelStyleTickComponent = oLabelStyle.TickComponents.Item(TICK_STYLE)
    On Error GoTo 0
    If (oLabelStyleTickComponent Is Nothing) Then
        Set oLabelStyleTickComponent = oLabelStyle.TickComponents.Add(TICK_STYLE)
    End If
    ' Specify what kind of symbol is used for the tick.
    oLabelStyleTickComponent.BlockName = "AeccTickLine"
    oLabelStyleTickComponent.Lineweight.Value = 60 ' .60 mm
    oLabelStyleTickComponent.AlignWithObject = True ' perpendicular to alignment
    oLabelStyleTickComponent.Angle = 0# ' in degrees
    oLabelStyleTickComponent.Visibility = True
    
    ' Add a line style to the crest curve style set.  This
    ' style governs the properties of a line placed at each
    ' crest curve.
    On Error Resume Next
    oLabelStyle.LineComponents.Remove LINE_STYLE
    Set oLabelStyleLineComponent = oLabelStyle.LineComponents.Item(LINE_STYLE)
    On Error GoTo 0
    If (oLabelStyleLineComponent Is Nothing) Then
        Set oLabelStyleLineComponent = oLabelStyle.LineComponents.Add(LINE_STYLE)
    End If
    oLabelStyleLineComponent.color = 40 ' orange-yellow
    oLabelStyleLineComponent.Angle = 2.094 ' radians, = 120 degrees
    oLabelStyleLineComponent.Length = -0.015 ' in whatever units are used in the drawing
    oLabelStyleLineComponent.StartPointXOffset = 0.0005
    oLabelStyleLineComponent.StartPointYOffset = 0
    oLabelStyleLineComponent.Visibility = True

    ' Add a line style to the crest curve style set.  This
    ' style governs the properties of a symbol placed at each
    ' crest curve. We will use this to add a circular tick
    ' mark.
    On Error Resume Next
    oLabelStyle.BlockComponents.Remove BLOCK_STYLE
    Set oLabelStyleBlockComponent = oLabelStyle.BlockComponents.Item(BLOCK_STYLE)
    On Error GoTo 0
    If (oLabelStyleBlockComponent Is Nothing) Then
        Set oLabelStyleBlockComponent = oLabelStyle.BlockComponents.Add(BLOCK_STYLE)
    End If
    oLabelStyleBlockComponent.BlockName = "AeccTickCircle"
    oLabelStyleBlockComponent.Visibility = True
    
    
    ' The major station label style automatically comes with a
    ' TextComponent named "Station".  Text componets like this
    ' one are for specifying what text is displayed at each
    ' station, and for managing how that text looks.  We will
    ' change what text is displayed, and move it under and to
    ' the side of each station anchor.
    
    Set oLabelStyleTextComponent = oLabelStyle.TextComponents.Item(0)
    ' Curve the text to follow the curves of the alignment.
    oLabelStyleTextComponent.AllowToCurve = True
    oLabelStyleTextComponent.Angle = 0#
    oLabelStyleTextComponent.XOffset = 0.01
    oLabelStyleTextComponent.YOffset = -0.015 - oLabelStyleTextComponent.Height
    oLabelStyleTextComponent.Contents = "STA=<[Station Value(Uft|FS|P2|RN|AP|Sn|TP|B2|EN|W0|OF)]>"
    oLabelStyleTextComponent.color = 253 ' light grey

    ' End of setting the crest curve style set.
    ' -------------------------------------------------------

    Set oCrestCurveStyle = oProfileLabelStyleSet.CrestCurvesLabelStyleSet.Add(oLabelStyle)
    oCrestCurveStyle.DimensionAnchorOption = aeccLabelAnchorDistanceAbove
    oCrestCurveStyle.DimensionAnchorValue = 0


    ' -------------------------------------------------------
    ' This section demonstrates how to set the major station
    ' label style.

    Dim oMajorStationStyle As AeccLabelStyleSetItem

    ' Create a new label style for our crest curves and
    ' add it to the drawing's collection of profile label
    ' styles.
    Set oLabelStyle = Nothing
    On Error Resume Next
    g_oDocument.ProfileLabelStyles.MajorStationLabelStyles.Remove STATION_LABEL_STYLE_SET
    Set oLabelStyle = g_oDocument.ProfileLabelStyles.MajorStationLabelStyles.Item(STATION_LABEL_STYLE_SET)
    On Error GoTo 0
    If (oLabelStyle Is Nothing) Then
        Set oLabelStyle = g_oDocument.ProfileLabelStyles.MajorStationLabelStyles.Add(STATION_LABEL_STYLE_SET)
    End If

    ' Add a line style to the crest curve style set.  This
    ' style governs the properties of a line placed at each
    ' crest curve.
    On Error Resume Next
    oLabelStyle.LineComponents.Remove LINE_STYLE2
    Set oLabelStyleLineComponent = oLabelStyle.LineComponents.Item(LINE_STYLE2)
    On Error GoTo 0
    If (oLabelStyleLineComponent Is Nothing) Then
        Set oLabelStyleLineComponent = oLabelStyle.LineComponents.Add(LINE_STYLE2)
    End If
    oLabelStyleLineComponent.color = 40 ' orange-yellow
    oLabelStyleLineComponent.Angle = 2.094 ' radians, = 120 degrees
    oLabelStyleLineComponent.Length = -0.015 ' in whatever units are used in the drawing
    oLabelStyleLineComponent.StartPointXOffset = 0.0005
    oLabelStyleLineComponent.StartPointYOffset = 0
    oLabelStyleLineComponent.Visibility = True

    ' Add a line style to the crest curve style set.  This
    ' style governs the properties of a symbol placed at each
    ' crest curve. We will use this to add a circular tick
    ' mark.
    On Error Resume Next
    oLabelStyle.BlockComponents.Remove BLOCK_STYLE2
    Set oLabelStyleBlockComponent = oLabelStyle.BlockComponents.Item(BLOCK_STYLE2)
    On Error GoTo 0
    If (oLabelStyleBlockComponent Is Nothing) Then
        Set oLabelStyleBlockComponent = oLabelStyle.BlockComponents.Add(BLOCK_STYLE2)
    End If
    oLabelStyleBlockComponent.BlockName = "AeccTickCircle"
    oLabelStyleBlockComponent.Visibility = True
    
    
    ' The major station label style automatically comes with a
    ' TextComponent named "Station".  Text componets like this
    ' one are for specifying what text is displayed at each
    ' station, and for managing how that text looks.  We will
    ' change what text is displayed, and move it under and to
    ' the side of each station anchor.
    
    Set oLabelStyleTextComponent = oLabelStyle.TextComponents.Item(0)
    ' Curve the text to follow the curves of the alignment.
    oLabelStyleTextComponent.AllowToCurve = True
    oLabelStyleTextComponent.Angle = 0#
    oLabelStyleTextComponent.XOffset = 0.01
    oLabelStyleTextComponent.YOffset = -0.015 - oLabelStyleTextComponent.Height
    oLabelStyleTextComponent.Contents = "STA=<[Station Value(Uft|FS|P2|RN|AP|Sn|TP|B2|EN|W0|OF)]>"
    oLabelStyleTextComponent.color = 253 ' light grey
    oLabelStyleTextComponent.Visibility = True

    ' End of setting the crest curve style set.
    ' -------------------------------------------------------

    '
    Dim oMajorStationLabelStyleSet As AeccLabelMajorStationStyleSetItem
    Dim dIncrement As Double
    dIncrement = 50#
    For i = 0 To oProfileLabelStyleSet.MajorStationLabelStyleSet.Count - 1
        If (oProfileLabelStyleSet.MajorStationLabelStyleSet.Item(i).Style.Name = oLabelStyle.Name) Then
            oProfileLabelStyleSet.MajorStationLabelStyleSet.Remove i
        End If
    Next i
    Set oMajorStationLabelStyleSet = oProfileLabelStyleSet.MajorStationLabelStyleSet.Add(oLabelStyle, dIncrement)

    CreateProfileLabelStyleSet = True
End Function ' CreateProfileLabelStyleSet

'''---------------------------------------------------------
'
'功能：创建纵断面图标注栏集式
'
'作者：
'
'
'日期：２００７/０8
'
'
'修改记录：无
'
'
''-----------------------------------------------------------
'
Public Function CreateBandStyleSet(sStyleName As String) As Boolean
    ' Remove any old band style set with the same name that
    ' might exist and create a new band.  It might be that
    ' the style is in use, and cannot be removed.  In that
    ' case, we will use the existing style.  We use the
    ' name given to us in the sStyleName parameter so that
    ' the calling function knows what name the style set
    ' is, and can access it.
    Dim oPVBandStyleSet As AeccProfileViewBandStyleSet
    On Error Resume Next
    g_oDocument.ProfileViewBandStyleSets.Remove sStyleName
    Set oPVBandStyleSet = g_oDocument.ProfileViewBandStyleSets.Add(sStyleName)
    On Error GoTo 0
    If (oPVBandStyleSet Is Nothing) Then
        On Error Resume Next
        Set oPVBandStyleSet = g_oDocument.ProfileViewBandStyleSets.Item(sStyleName)
        On Error GoTo 0
        If (oPVBandStyleSet Is Nothing) Then
            Debug.Print "Error trying to create a band style set."
            CreateBandStyleSet = False
            Exit Function
        End If
    End If

    ''''''''''''''''''''''''''''''''''''''''''''''''
    ' Add a profile information data band
    
    ' We will modify the style set by adding a profile
    ' band - a band that describes basic information of
    ' profile geometry at station tick marks.
    '
    ' Remove any old profile band styles that might exist
    ' and create a new style.  It might be that the style
    ' is in use, and cannot be removed.  In that case, we
    ' will use the existing style.
    Dim oBandProfileDataStyle As AeccBandProfileDataStyle
    On Error Resume Next
    g_oDocument.ProfileViewBandStyles.ProfileDataBandStyles.Remove "PROFILEVIEW_PROFILE_BAND_STYLE_01"
    Set oBandProfileDataStyle = g_oDocument.ProfileViewBandStyles.ProfileDataBandStyles.Add("PROFILEVIEW_PROFILE_BAND_STYLE_01")
    On Error GoTo 0
    If (oBandProfileDataStyle Is Nothing) Then
        On Error Resume Next
        Set oBandProfileDataStyle = g_oDocument.ProfileViewBandStyles.ProfileDataBandStyles.Item("PROFILEVIEW_PROFILE_BAND_STYLE_01")
        On Error GoTo 0
        If (oBandProfileDataStyle Is Nothing) Then
            Debug.Print "Error trying to create a profile band style."
            CreateBandStyleSet = False
            Exit Function
        End If
    End If

    ' Add ticks and labels to each horizontal geography location.
    With oBandProfileDataStyle
        .HGPLabelDisplayStyle2d.Visible = True
        .HGPTickDisplayStyle2d.color = 10 ' red
        .HGPTickDisplayStyle2d.Visible = True
        .HGPLabelStyle.TextComponents.Item(0).Contents = "<[Station Value(Uft|FS|P0|RN|AP|Sn|TP|B2|EN|W0|OF)]>"
        .HGPLabelStyle.TextComponents.Item(0).color = 11 ' light red
        .HGPLabelStyle.TextComponents.Item(0).Visibility = True
    End With
    
    ' Modify how the title is displayed.
    With oBandProfileDataStyle
        .TitleBoxDisplayStyle2d.color = 10 ' red
        .TitleBoxDisplayStyle2d.Linetype = "DOT"
        .TitleBoxDisplayStyle2d.Visible = True
        .TitleBoxTextDisplayStyle2d.color = 80 ' green
        .TitleBoxTextDisplayStyle2d.Visible = True
        .TitleStyle.Text = "Profile Info"
        .TitleStyle.TextHeight = 0.0125
        .TitleStyle.TextBoxWidth = 0.21
    End With
    
    ' Hide the rest of the information locations.
    With oBandProfileDataStyle
        .VGPLabelStyle.TextComponents.Item(0).Visibility = False
        .MajorIncrementLabelStyle.TextComponents.Item(0).Visibility = False
        .MajorStationLabelDisplayStyle2d.Visible = False
        .MajorTickDisplayStyle2d.Visible = False
        .MinorIncrementLabelStyle.TextComponents.Item(0).Visibility = False
        .MinorStationLabelDisplayStyle2d.Visible = False
        .MinorTickDisplayStyle2d.Visible = False
        .VGPLabelDisplayStyle2d.Visible = False
        .VGPTickDisplayStyle2d.Visible = False
        .StationEquationLabelStyle.TextComponents.Item(0).Visibility = True
        .StationEquationLabelDisplayStyle2d.Visible = True
        .StationEquationTickDisplayStyle2d.Visible = True
    End With
    
    ' Finally, we add the profile information style to
    ' the profile view style set we created earlier.
    Dim oBandStyleSetItem As AeccBandStyleSetItem
    Set oBandStyleSetItem = oPVBandStyleSet.Add(oBandProfileDataStyle)
    
    
    ''''''''''''''''''''''''''''''''''''''''''''''''
    ' Add a horizontal geometry data band
    
    ' We will modify the style set by adding a geometry
    ' band - a band that describes the horizontal slopes
    ' of each segment of the profile geometry.
    '
    ' Remove any old horizontal geometry band styles that
    ' might exist and create a new style.  It might be
    ' that the style is in use, and cannot be removed.  In
    ' that case, we will use the existing style.
    Dim oBandHorizontalGeometryStyle As AeccBandHorizontalGeometryStyle
    On Error Resume Next
    g_oDocument.ProfileViewBandStyles.HorizontalGeometryBandStyles.Remove "PROFILEVIEW_HORIZONTAL_BAND_STYLE_01"
    Set oBandHorizontalGeometryStyle = g_oDocument.ProfileViewBandStyles.HorizontalGeometryBandStyles.Add("PROFILEVIEW_HORIZONTAL_BAND_STYLE_01")
    On Error GoTo 0
    If (oBandHorizontalGeometryStyle Is Nothing) Then
        On Error Resume Next
        Set oBandHorizontalGeometryStyle = g_oDocument.ProfileViewBandStyles.HorizontalGeometryBandStyles.Item("PROFILEVIEW_HORIZONTAL_BAND_STYLE_01")
        On Error GoTo 0
        If (oBandHorizontalGeometryStyle Is Nothing) Then
            Debug.Print "Error trying to create a horizontal band style."
            CreateBandStyleSet = False
            Exit Function
        End If
    End If

    With oBandHorizontalGeometryStyle
        ' Add displays and labels for alignment tangents.
        .TangentGeometryDisplayStyle2d.Visible = True
        .TangentGeometryDisplayStyle2d.color = 160 ' blue
        .TangentLabelDisplayStyle2d.Visible = True
        .TangentLabelStyle.TextComponents.Item(0).Contents = "Length = <[Length(Uft|P2|RN|Sn|OF|AP)]>"
        .TangentLabelStyle.TextComponents.Item(0).color = 120 ' light blue
        .TangentLabelStyle.TextComponents.Item(0).Visibility = True
    
        ' Add displays and labels for alignment curves.
        .CurveGeometryDisplayStyle2d.Visible = True
        .CurveGeometryDisplayStyle2d.color = 160 ' blue
        .CurveLabelDisplayStyle2d.Visible = True
        .CurveLabelStyle.TextComponents.Item(0).Contents = "Length = <[Length(Uft|P2|RN|Sn|OF|AP)]>"
        .CurveLabelStyle.TextComponents.Item(0).color = 120 ' light blue
        .CurveLabelStyle.TextComponents.Item(0).Visibility = True
    
        ' Add tick marks at each horizontal geometry point,
        ' the location where different segments of the
        ' alignment meet.  Make it the same color as the
        ' horizontal geometry points in the first data band.
        .TickDisplayStyle2d.color = 10 ' red
        .TickDisplayStyle2d.Visible = True
        
        ' Modify how the title is displayed.
        .TitleBoxDisplayStyle2d.color = 10 ' red
        .TitleBoxDisplayStyle2d.Linetype = "DOT"
        .TitleBoxDisplayStyle2d.Visible = True
        .TitleBoxTextDisplayStyle2d.color = 80 ' green
        .TitleBoxTextDisplayStyle2d.Visible = True
        .TitleStyle.Text = "Alignment Geometry"
        .TitleStyle.TextHeight = 0.0125
        .TitleStyle.TextBoxWidth = 0.21
        
        ' Hide the rest of the information locations and
        ' graphical displays.
        .SpiralGeometryDisplayStyle2d.Visible = False
        .SpiralLabelDisplayStyle2d.Visible = False
    End With
    
    ' Finally, we add the vertical geometry style to the
    ' profile view style set we created earlier.
    Set oBandStyleSetItem = oPVBandStyleSet.Add(oBandHorizontalGeometryStyle)


    ''''''''''''''''''''''''''''''''''''''''''''''''
    ' Add a Vertical Geometry data band
    
    ' We will modify the style set by adding a geometry
    ' band - a band that describes the vertical slopes
    ' of each segment of the profile geometry.
    '
    ' Remove any old vertical geometry band styles that
    ' might exist and create a new style.  It might be
    ' that the style is in use, and cannot be removed.  In
    ' that case, we will use the existing style.
    Dim oBandVerticalGeometryStyle As AeccBandVerticalGeometryStyle
    On Error Resume Next
    g_oDocument.ProfileViewBandStyles.VerticalGeometryBandStyles.Remove "PROFILEVIEW_VERTICAL_BAND_STYLE_01"
    Set oBandVerticalGeometryStyle = g_oDocument.ProfileViewBandStyles.VerticalGeometryBandStyles.Add("PROFILEVIEW_VERTICAL_BAND_STYLE_01")
    On Error GoTo 0
    If (oBandVerticalGeometryStyle Is Nothing) Then
        On Error Resume Next
        Set oBandVerticalGeometryStyle = g_oDocument.ProfileViewBandStyles.VerticalGeometryBandStyles.Item("PROFILEVIEW_VERTICAL_BAND_STYLE_01")
        On Error GoTo 0
        If (oBandVerticalGeometryStyle Is Nothing) Then
            Debug.Print "Error trying to create a vertical band style."
            CreateBandStyleSet = False
            Exit Function
        End If
    End If

    With oBandVerticalGeometryStyle
        ' Add graphical marks that show the uphill or downhill
        ' directions and the lengths of the vertical segments
        ' of the profile.  On uphill sections the label of the
        ' length of the segment will be in white, on downhill
        ' it will be pale yellow.
        .DownhillTangentLabelStyle.TextComponents.Item(0).Contents = "<[Tangent Horizontal Length(Uft|P2|RN|Sn|OF|AP)]>"
        .DownhillTangentLabelStyle.TextComponents.Item(0).color = 51 ' pale yellow
        .DownhillTangentLabelStyle.TextComponents.Item(0).Visibility = True
        .UphillTangentLabelStyle.TextComponents.Item(0).Contents = "<[Tangent Horizontal Length(Uft|P2|RN|Sn|OF|AP)]>"
        .UphillTangentLabelStyle.TextComponents.Item(0).color = 255  ' white
        .UphillTangentLabelStyle.TextComponents.Item(0).Visibility = True
        .TangentGeometryDisplayStyle2d.color = 220 ' pink
        .TangentGeometryDisplayStyle2d.Visible = True
        .TangentLabelDisplayStyle2d.Visible = True
        .TangentGeometryDisplayStyle2d.Visible = True
        
        ' Modify how the title is displayed.
        .TitleBoxDisplayStyle2d.color = 10 ' red
        .TitleBoxDisplayStyle2d.Linetype = "DOT"
        .TitleBoxDisplayStyle2d.Visible = True
        .TitleBoxTextDisplayStyle2d.color = 80 ' green
        .TitleBoxTextDisplayStyle2d.Visible = True
        .TitleStyle.Text = "Profile Geometry"
        .TitleStyle.TextHeight = 0.0125
        .TitleStyle.TextBoxWidth = 0.21
    
        ' Hide the rest of the information locations and
        ' graphical displays.
        .CurveGeometryDisplayStyle2d.Visible = False
        .CurveLabelDisplayStyle2d.Visible = False
        .TickDisplayStyle2d.Visible = False
    End With
    
    ' Finally, we add the vertical geometry style to the
    ' profile view style set we created earlier.
    Set oBandStyleSetItem = oPVBandStyleSet.Add(oBandVerticalGeometryStyle)


    ''''''''''''''''''''''''''''''''''''''''''''''''
    ' Add a Superelevation data band
    
    ' We will modify the style set by adding a
    ' superelevation band - a band that describes the
    ' superelevation of the alignment along the length
    ' of the profile view.
    '
    ' Remove any old superelevation geometry band styles
    ' that might exist and create a new style.  It might
    ' be that the style is in use, and cannot be removed.
    ' In that case, we will use the existing style.
    Dim oBandSuperElevationStyle As AeccBandSuperElevationStyle
    On Error Resume Next
    g_oDocument.ProfileViewBandStyles.SuperElevationBandStyles.Remove "PROFILEVIEW_SUPERELEVATION_BAND_STYLE_01"
    Set oBandSuperElevationStyle = g_oDocument.ProfileViewBandStyles.SuperElevationBandStyles.Add("PROFILEVIEW_SUPERELEVATION_BAND_STYLE_01")
    On Error GoTo 0
    If (oBandSuperElevationStyle Is Nothing) Then
        On Error Resume Next
        Set oBandSuperElevationStyle = g_oDocument.ProfileViewBandStyles.SuperElevationBandStyles.Item("PROFILEVIEW_SUPERELEVATION_BAND_STYLE_01")
        On Error GoTo 0
        If (oBandSuperElevationStyle Is Nothing) Then
            Debug.Print "Error trying to create a superelevation band style."
            CreateBandStyleSet = False
            Exit Function
        End If
    End If

    With oBandSuperElevationStyle
        ' Add graphical display of the slope of the
        ' left and right outside shoulders.  If the
        ' line is above the centerline, then the slope
        ' is positive.
        .LeftOutsideShoulderLineDisplayStyle2d.Visible = True
        .LeftOutsideShoulderLineDisplayStyle2d.color = 151 ' pale blue
        .RightOutsideShoulderLineDisplayStyle2d.Visible = True
        .RightOutsideShoulderLineDisplayStyle2d.color = 51 ' pale yellow
        
        ' Add a reference line through the center of the
        ' data band.
        .ReferenceLineDisplayStyle2d.Visible = True
        .ReferenceLineDisplayStyle2d.color = 252 ' gray
        
        ' Display a marker when the crown returns to
        ' normal.
        .NormalCrownLabelDisplayStyle2d.Visible = True
        .NormalCrownTickDisplayStyle2d.Visible = True
        .NormalCrownLocationLabelStyle.TextComponents.Item(0).Contents = "Begin Normal - <[Station Value(Uft|FS|P2|RN|AP|Sn|TP|B2|EN|W0|OF)]>"

        ' Modify how the title is displayed.
        .TitleBoxDisplayStyle2d.color = 10 ' red
        .TitleBoxDisplayStyle2d.Linetype = "DOT"
        .TitleBoxDisplayStyle2d.Visible = True
        .TitleBoxTextDisplayStyle2d.color = 80 ' green
        .TitleBoxTextDisplayStyle2d.Visible = True
        .TitleStyle.Text = "Profile Geometry"
        .TitleStyle.TextHeight = 0.0125
        .TitleStyle.TextBoxWidth = 0.21
    
        ' Hide the rest of the information locations and
        ' graphical displays.
        '.LeftOutsideShoulderLineDisplayStyle2d.Visible = False
        '.RightOutsideShoulderLineDisplayStyle2d.Visible = False
        '.ReferenceLineDisplayStyle2d.Visible = False
        '.NormalCrownLabelDisplayStyle2d.Visible = False
        '.NormalCrownTickDisplayStyle2d.Visible = False
        .FullSuperLabelDisplayStyle2d.Visible = False
        .FullSuperTickDisplayStyle2d.Visible = False
        .LeftInsidePavementLineDisplayStyle2d.Visible = False
        .LeftInsideShoulderLineDisplayStyle2d.Visible = False
        .LeftOutsidePavementLineDisplayStyle2d.Visible = False
        .LevelCrownLabelDisplayStyle2d.Visible = False
        .LevelCrownTickDisplayStyle2d.Visible = False
        .ReverseCrownLabelDisplayStyle2d.Visible = False
        .ReverseCrownTickDisplayStyle2d.Visible = False
        .RightInsidePavementLineDisplayStyle2d.Visible = False
        .RightInsideShoulderLineDisplayStyle2d.Visible = False
        .RightOutsidePavementLineDisplayStyle2d.Visible = False
        .ShoulderBreakOverLabelDisplayStyle2d.Visible = False
        .ShoulderBreakOverTickDisplayStyle2d.Visible = False
        .TransitionSegmentLabelDisplayStyle2d.Visible = False
    End With

    ' Finally, we add the superelevation style to the
    ' profile view style set we created earlier.
    Set oBandStyleSetItem = oPVBandStyleSet.Add(oBandSuperElevationStyle)


    ''''''''''''''''''''''''''''''''''''''''''''''''
    ' We are done.  Return true.
    CreateBandStyleSet = True
End Function ' CreateBandStyleSet

Attribute VB_Name = "Subroutines"
'
' MODULE_ID {Subroutines.bas}
' {ProfileSample.dvb}
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

'''---------------------------------------------------------
'
'功能：创建纵断面和纵断面图
'
'作者：
'
'
'日期：２００７/０8
'
'
'修改记录：无
'
'
''-----------------------------------------------------------
Sub RunProfile()
    

    If ThisDrawing.Name <> "Profile_CH07.dwg" Then
        MsgBox "请打开Profile_CH07.dwg后重新运行"
        Exit Sub
    
    End If
    
    ' 获取程序和文档对象
    If (GetBaseCivilObjects = False) Then
        MsgBox "获取程序和文档对象失败，退出."
        Exit Sub
    End If

    Dim pt As Variant
    Dim oEnt As AcadObject
    
    ThisDrawing.Utility.GetEntity oEnt, pt, "选择路线对象"
    If oEnt.ObjectName <> "AeccDbAlignment" Then
         MsgBox "选择的对象不是路线对象，退出."
        Exit Sub
    End If
    Dim oAlignment As AeccAlignment
    Set oAlignment = oEnt

    If (CreateProfile(oAlignment) = False) Then
        MsgBox "基于路线和曲面创建纵断面失败."
        Exit Sub
    End If

    If (CreateProfileView(oAlignment) = False) Then
        MsgBox "创建纵断面图失败."
        Exit Sub
    End If
    
    g_oCivilApp.ZoomExtents
End Sub
