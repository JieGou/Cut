Attribute VB_Name = "BaseObjects"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' 声明全局的程序、文档和数据库对象
Public g_oCivilApp As AeccApplication
Public g_oDocument As AeccDocument
Public g_oAeccDb As AeccDatabase


''---------------------------------------------------------
'
'功能：获取模块的程序、文档和数据库对象
'
'作者：
'
'
'日期：２００７/０8
'
'
'修改记录：无
'
'
''-----------------------------------------------------------
Public Function GetBaseCivilObjects() As Boolean
    Dim oApp As AcadApplication
    Set oApp = ThisDrawing.Application
    '需要指定版本号（5.0）.
    Const sAppName = "AeccXUiLand.AeccApplication.5.0"
    Set g_oCivilApp = oApp.GetInterfaceObject(sAppName)
    If g_oCivilApp Is Nothing Then
        MsgBox "获取程序对象 " & sAppName & "错误, 退出."
        GetBaseCivilObjects = False
        Exit Function
    End If
    Set g_oDocument = g_oCivilApp.ActiveDocument
    Set g_oAeccDb = g_oDocument.Database
    GetBaseCivilObjects = True
End Function

Attribute VB_Name = "Parcel"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
Option Explicit


''---------------------------------------------------------
'
'功能：创建地块和显示地块属性
'
'作者：
'
'
'日期：２００７/０8
'
'
'修改记录：无
'
'
''-----------------------------------------------------------
Public Function CreateParcel() As Boolean
    Dim i, j, k, l As Integer
    Dim oParcelLoop As AeccParcelLoop
    Dim oParcels As AeccParcels

    ' 获取场地
    Dim oSite As AeccSite
    Set oSite = g_oDocument.Sites.Item("SITE_01")
    If (oSite Is Nothing) Then
        Debug.Print "获取场地失败."
        CreateParcel = False
        Exit Function
    End If
    
    Set oParcels = oSite.Parcels

    ' 使用地块线段创建地块对象
    Dim oSegment As AeccParcelSegment

    '
    Call oSite.ParcelSegments.AddLine(50, 275, 150, 275)
    ' 地块 1
    Set oSegment = oSite.ParcelSegments.AddLine(0, 0, 0, 200)
    Call oSite.ParcelSegments.AddCurve(0, 200, -0.5, 200, 200)
    Call oSite.ParcelSegments.AddLine(200, 200, 200, 0)
    Call oSite.ParcelSegments.AddLine(200, 0, 0, 0)
    ' Parcel 2, which shares a segment with parcel 1
    Call oSite.ParcelSegments.AddCurve2(200, 200, 330, 180, 400, 200)
    Call oSite.ParcelSegments.AddLine(400, 200, 400, 0)

    ' 地块 2和3.
    Dim oPolyline As AcadPolyline
    Dim dPoints(0 To 8) As Double
    dPoints(0) = 400: dPoints(1) = 0: dPoints(2) = 0
    dPoints(3) = 325: dPoints(4) = 25: dPoints(5) = 0
    dPoints(6) = 200: dPoints(7) = 0: dPoints(8) = 0
    Set oPolyline = g_oDocument.Database.ModelSpace.AddPolyline(dPoints)
    oPolyline.Closed = True
    ' 设置第二个参数为True，将在地块形成后会删除多段线
    Call oSite.ParcelSegments.AddFromEntity(oPolyline, True)

    g_oCivilApp.Update
    g_oCivilApp.ZoomExtents

    '
    ' 查询和显示地块属性
    '
    Dim oParcel As AeccParcel
    ' 遍历所有地块.
    For i = 0 To oParcels.Count - 1
        Set oParcel = oParcels.Item(i)
        
        MsgBox "地块名称: " & oParcel.Name & vbLf _
            & "     面积: " & oParcel.Statistics.Area & vbLf _
            & "     周长: " & oParcel.Statistics.Perimeter
        Debug.Print "Parcel name: " & oParcel.Name
        
        
        Debug.Print "number of loops: " & CStr(oParcel.ParcelLoops.Count)
        ' 遍历地块的组成
        For j = 0 To oParcel.ParcelLoops.Count - 1
            Set oParcelLoop = oParcel.ParcelLoops.Item(j)
            Debug.Print "组成地块的实体数目: " & CStr(oParcelLoop.Count)
            ' 遍历地块的所有组成实体
            For k = 0 To oParcelLoop.Count - 1
                Dim oSegmentElement As AeccParcelSegmentElement
                Set oSegmentElement = oParcelLoop.Item(k)
                
                Debug.Print "   构成要素 " & CStr(k) & ":从起点 " & CStr(oParcelLoop.Item(k).StartX) & "," & CStr(oParcelLoop.Item(k).StartY) & " 到 " & CStr(oParcelLoop.Item(k).EndX) & ", " & CStr(oParcelLoop.Item(k).EndY)

                If (TypeOf oSegmentElement Is AeccParcelSegmentLine) Then
                    Dim oSegmentLine As AeccParcelSegmentLine
                    Set oSegmentLine = oSegmentElement
                    Debug.Print "      是直线. "
                ElseIf (TypeOf oSegmentElement Is AeccParcelSegmentCurve) Then
                    Dim oSegmentCurve As AeccParcelSegmentCurve
                    Set oSegmentCurve = oSegmentElement
                    Debug.Print "      是一段曲线，其半径:" & oSegmentCurve.Radius
                End If
            Next k
        Next j
    Next i

    
    CreateParcel = True
End Function ' CreateParcel

Attribute VB_Name = "Site"
'
' MODULE_ID {Site.bas}
' {ParcelSample.dvb}
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
''---------------------------------------------------------
'
'功能：创建场地
'
'作者：
'
'
'日期：２００７/０8
'
'
'修改记录：无
'
'
''-----------------------------------------------------------
Public Function CreateSite() As Boolean
    Dim oSites As AeccSites
    Set oSites = g_oDocument.Sites
    Dim oSite As AeccSite
    
    On Error Resume Next
    Set oSite = oSites.Item("SITE_01")
    On Error GoTo 0
    If (oSite Is Nothing) Then
        On Error Resume Next
        Set oSite = oSites.Add("SITE_01")
        On Error GoTo 0
        If (oSite Is Nothing) Then
            Debug.Print "创建场地失败."
            CreateSite = False
            Exit Function
        End If
    End If


    oSite.NextAutoCounterParcel = 300
    
    CreateSite = True
End Function

Attribute VB_Name = "Subroutines"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
Option Explicit


'
''---------------------------------------------------------
'
'功能：创建场地和地块
'
'作者：
'
'
'日期：２００７/０8
'
'
'修改记录：无
'
'
''-----------------------------------------------------------
'
Sub CreateParcels()
    ' 获取程序对象等
    If (GetBaseCivilObjects() = False) Then
        Exit Sub
    End If
    
    If (CreateSite() = False) Then
        Debug.Print "创建场地失败."
        Exit Sub
    End If

    If (CreateParcel() = False) Then
        Debug.Print "创建地块失败."
        Exit Sub
    End If
    
    g_oCivilApp.Update
End Sub
