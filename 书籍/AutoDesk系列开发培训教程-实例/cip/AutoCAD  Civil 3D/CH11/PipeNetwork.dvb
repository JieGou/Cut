Attribute VB_Name = "CreatePipe"
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'

Option Explicit

    

''---------------------------------------------------------
'
'功能：创建管道网络（不需要用户交互，数据固定）
'
'输入参数：
'
'
'输出参数：Boolean
'
'
'作者：
'
'
'日期：２００７/０8
'
'
'修改记录：无
'
'
''-----------------------------------------------------------
Public Function CreatePipeNetwork() As Boolean



    Dim oNetworks As AeccPipeNetworks
    Dim oNetwork As AeccPipeNetwork
    Dim index As Integer
    Dim oSettings As AeccPipeSettingsRoot
    Dim oPartLists As AeccPartLists
    Dim oPartList As AeccPartList
    Dim oPartFamily As AeccPartFamily
    Dim oSizeFilters As AeccPartSizeFilters
    Dim oSizeFilter As AeccPartSizeFilter
    Dim sStructureGuid As String
    Dim sPipeGuid As String
    Dim oStructureFilter As AeccPartSizeFilter
    Dim oPipeFilter As AeccPartSizeFilter
    Dim oPipe As AeccPipe
    
    ' 获取管网集合
    Set oNetworks = g_oPipeDocument.PipeNetworks
    Set oNetwork = Nothing
    '搜索"NETWORK_NAME" 的管网
    On Error Resume Next
    Set oNetwork = oNetworks.Item("NETWORK_NAME")
    On Error GoTo 0
    '如果"NETWORK_NAME" 管网不存在，则创建
    If (oNetwork Is Nothing) Then
        Set oNetwork = oNetworks.Add("NETWORK_NAME")
    End If

    ' 创建管道样式.
    Dim oPipeStyle As AeccPipeStyle
    Set oPipeStyle = CreatePipeStyle("PIPE_STYLE_NAME")
    ' 创建结构样式.
    Dim oStructureStyle As AeccStructureStyle
    Set oStructureStyle = CreateStructureStyle("STRUCTURE_STYLE_NAME")
    If ((oPipeStyle Is Nothing) Or (oStructureStyle Is Nothing)) Then
        Exit Function
    End If
    
    '
    '从零件目录中选择第一个零件（管道和结构）,选中的零件用于后面的管网的创建
    '
    Set oSettings = g_oPipeDocument.Settings
    ' 获取零件列表集合
    Set oPartLists = oSettings.PartLists
    ' 获取找到的第一个零件列表
    Set oPartList = oPartLists.Item(0)
    For Each oPartFamily In oPartList
        ' 查找管道族
        ThisDrawing.Utility.Prompt ("零件族:" + oPartFamily.Name + vbCrLf)
        If (oPartFamily.Domain = aeccDomPipe) Then
            sPipeGuid = oPartFamily.GUID
            ' 从零件族中获取第一个零件族尺寸（设定管道）
            Set oPipeFilter = oPartFamily.SizeFilters.Item(0)
            ThisDrawing.Utility.Prompt ("   零件族尺寸:" + oPipeFilter.Name + vbCrLf)
            Exit For
        End If
    Next
    
    For Each oPartFamily In oPartList
        ThisDrawing.Utility.Prompt ("零件族:" + oPartFamily.Name + vbCrLf)
        ' 查找结构族("空结构"除外）
        If ((oPartFamily.Domain = aeccDomStructure) And (StrComp(oPartFamily.Name, "空结构", vbTextCompare) <> 0)) Then
            sStructureGuid = oPartFamily.GUID
            ' 从零件族中获取第一个零件族尺寸（设定结构）
            Set oStructureFilter = oPartFamily.SizeFilters.Item(0)
            ThisDrawing.Utility.Prompt ("   零件族尺寸:" + oStructureFilter.Name + vbCrLf)
            Exit For
        End If
    Next
    
    '''''''''''''''''''''''''''''''''''''''''''''''''''''
    ' 基于固定（指定）点创建管网
    Dim dEndPoint(0 To 2) As Double
    Dim vStartPoint As Variant
    Dim oStructure As AeccStructure
    
    ' 在结束点创建结构
    dEndPoint(0) = 10: dEndPoint(1) = 70:  dEndPoint(2) = -20
    Set oStructure = oNetwork.Structures.Add(sStructureGuid, oStructureFilter, dEndPoint, 5.2333) ' 305 degrees
    Set oStructure.Style = oStructureStyle
    
    ' 创建从结构开始的管道，在创建一个其他结构
    vStartPoint = dEndPoint
    dEndPoint(0) = 35: dEndPoint(1) = 30:  dEndPoint(2) = -20
    Set oPipe = oNetwork.Pipes.Add(sPipeGuid, oPipeFilter, vStartPoint, dEndPoint)
    oPipe.ConnectToStructure aeccPipeStart, oStructure
    Set oStructure = oNetwork.Structures.Add(sStructureGuid, oStructureFilter, dEndPoint, 5.236)
    oPipe.ConnectToStructure aeccPipeEnd, oStructure
    oPipe.FlowDirectionMethod = aeccPipeFlowDirectionMethodStartToEnd
    ThisDrawing.Utility.Prompt ("管道1长度:" + CStr(oPipe.Length2D) + vbCrLf)
    Set oPipe.Style = oPipeStyle
    Set oStructure.Style = oStructureStyle
    
    ' 从前一结构绘制弯管
    vStartPoint = dEndPoint
    dEndPoint(0) = 65: dEndPoint(1) = 30:  dEndPoint(2) = -20
    Set oPipe = oNetwork.Pipes.AddCurvedPipe(sPipeGuid, oPipeFilter, vStartPoint, dEndPoint, 45, False)
    oPipe.ConnectToStructure aeccPipeStart, oStructure
    oPipe.FlowDirectionMethod = aeccPipeFlowDirectionMethodStartToEnd
    ThisDrawing.Utility.Prompt ("管道2长度:" + CStr(oPipe.Length2D) + vbCrLf)
    Set oPipe.Style = oPipeStyle
    
    '
    '绘制直管连接，并和前面弯管相连，最后创建结构
    '
    vStartPoint = dEndPoint
    dEndPoint(0) = 90: dEndPoint(1) = 70: dEndPoint(2) = -20
    Dim oPipeNew As AeccPipe
    Set oPipeNew = oNetwork.Pipes.Add(sPipeGuid, oPipeFilter, vStartPoint, dEndPoint)
    ' 将一个管道直接连接到另一个管道时，会自动在两个管道之间插入没有任何结构造型的空结构对象
    Set oStructure = oPipeNew.ConnectToPipe(aeccPipeStart, oPipe, aeccPipeEnd)
    '即便空结构在图形中不可见，也需要将某个样式指定给空结构
    Set oStructure.Style = oStructureStyle
    ' 添加结构
    Set oStructure = oNetwork.Structures.Add(sStructureGuid, oStructureFilter, dEndPoint, 0.9959)
    oPipeNew.ConnectToStructure aeccPipeEnd, oStructure
    oPipeNew.FlowDirectionMethod = aeccPipeFlowDirectionMethodStartToEnd
    ThisDrawing.Utility.Prompt ("管道3长度 :" + CStr(oPipeNew.Length2D) + vbCrLf)
    Set oPipeNew.Style = oPipeStyle
    Set oStructure.Style = oStructureStyle

    ' 缩放视口
    g_oPipeApplication.ZoomExtents
    
    CreatePipeNetwork = True
End Function

Attribute VB_Name = "PartList"
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.

Option Explicit

''---------------------------------------------------------
'
'功能：获取零件信息
'
'输入参数：
'
'输出参数：
'
'
'作者：
'
'
'日期：２００７/０8
'
'
'修改记录：无
'
'
''-----------------------------------------------------------

Public Sub PartList()

    Dim oSettings As AeccPipeSettingsRoot
    Dim oPartLists As AeccPartLists
    Dim oPartList As AeccPartList
    Dim oPartFamily As AeccPartFamily
    Dim oSizeFilters As AeccPartSizeFilters
    Dim oSizeFilter As AeccPartSizeFilter
    Dim sStructureGuid As String
    Dim sPipeGuid As String
    Dim oStructureFilter As AeccPartSizeFilter
    Dim oPipeFilter As AeccPartSizeFilter
    Dim oPartDataField As AeccPartDataField
    
    If GetPipeObjects = False Then
        MsgBox "获取管道程序对象失败，退出"
        Exit Sub
    End If
    
  
    ' 获取零件列表
    Set oSettings = g_oPipeDocument.Settings
    Set oPartLists = oSettings.PartLists
    ThisDrawing.Utility.Prompt ("零件列表数目: " + CStr(oPartLists.Count) + vbCrLf)
    
    ' 获取第一个零件列表
    For Each oPartList In oPartLists
      
        ThisDrawing.Utility.Prompt ("PART LIST - " + oPartList.Name + vbCrLf)
        ThisDrawing.Utility.Prompt ("------------------------------------------------" + vbCrLf)
        
        ' From the part list, looking at only those part families
        ' that are pipes, print all the individual parts.
        ThisDrawing.Utility.Prompt ("  管道族：" + vbCrLf)
        ThisDrawing.Utility.Prompt ("  =====" + vbCrLf)
        For Each oPartFamily In oPartList
            ' Look for only pipe families.
            If (oPartFamily.Domain = aeccDomPipe) Then
                sPipeGuid = oPartFamily.GUID
                ThisDrawing.Utility.Prompt ("  零件族: " + oPartFamily.Name + vbCrLf + "  GUID:" + sPipeGuid + vbCrLf)
                ' Go through each part in this family.
                For Each oPipeFilter In oPartFamily.SizeFilters
                    ThisDrawing.Utility.Prompt ("    管道过滤器: " + oPipeFilter.Name + vbCrLf)
                    
                    ' Print out all data fields for this pipe size.
                    ThisDrawing.Utility.Prompt ("   可用的数据段:" + vbCrLf)
                    ThisDrawing.Utility.Prompt ("    /*======" + vbCrLf)
                    For Each oPartDataField In oPipeFilter.PartDataRecord
                        ThisDrawing.Utility.Prompt ("      上下文名称:  " + oPartDataField.ContextString + vbCrLf)
                        ThisDrawing.Utility.Prompt ("      描      述:   " + oPartDataField.Description + vbCrLf)
                        ThisDrawing.Utility.Prompt ("      内部 名 称: " + oPartDataField.Name + vbCrLf)
                        ThisDrawing.Utility.Prompt ("      值        :" + CStr(oPartDataField.Tag) + vbCrLf)
                        ThisDrawing.Utility.Prompt ("      值   类 型: " + CStr(oPartDataField.Type) + vbCrLf)
                        ThisDrawing.Utility.Prompt ("    ======*/" + vbCrLf)
                    Next
                Next
            End If
        Next

        ' Perform the same action to get a structure filter from
        ' the first structure part family from the first part
        ' family we access.
        ThisDrawing.Utility.Prompt ("  结构" + vbCrLf)
        ThisDrawing.Utility.Prompt ("  ==========" + vbCrLf)
        For Each oPartFamily In oPartList
            ' Look for only structure families.
            If (oPartFamily.Domain = aeccDomStructure) Then
                sStructureGuid = oPartFamily.GUID
                ThisDrawing.Utility.Prompt ("  零件族: " + oPartFamily.Name + vbCrLf + "  GUID:" + sStructureGuid + vbCrLf)
                ' Go through each part in this family.
                For Each oStructureFilter In oPartFamily.SizeFilters
                    ThisDrawing.Utility.Prompt ("    结构过滤器: " + oStructureFilter.Name + vbCrLf)
                
                    ' Print out all data fields for this pipe size.
                    ThisDrawing.Utility.Prompt ("    可用的数据段:" + vbCrLf)
                    ThisDrawing.Utility.Prompt ("    /*======" + vbCrLf)
                    For Each oPartDataField In oStructureFilter.PartDataRecord
                        ThisDrawing.Utility.Prompt ("      上下文名称:  " + oPartDataField.ContextString + vbCrLf)
                        ThisDrawing.Utility.Prompt ("      描      述:   " + oPartDataField.Description + vbCrLf)
                        ThisDrawing.Utility.Prompt ("      内部 名 称: " + oPartDataField.Name + vbCrLf)
                        ThisDrawing.Utility.Prompt ("      值       : " + CStr(oPartDataField.Tag) + vbCrLf)
                        ThisDrawing.Utility.Prompt ("      值   类 型: " + CStr(oPartDataField.Type) + vbCrLf)
                        ThisDrawing.Utility.Prompt ("      ======*/" + vbCrLf)
                    Next
                Next
            End If
        Next
    Next


End Sub

Attribute VB_Name = "PipeObject"
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'

Option Explicit
' 声明全局的程序、文档和数据库对象
'
Public g_oPipeApplication As AeccPipeApplication
Public g_oPipeDocument As AeccPipeDocument
Public g_oPipeDatabase As AeccPipeDatabase




''---------------------------------------------------------
'
'功能：获取管道模块的程序、文档和数据库对象
'
'作者：
'
'
'日期：２００７/０8
'
'
'修改记录：无
'
'
''-----------------------------------------------------------
Function GetPipeObjects() As Boolean
    Dim oApp As AcadApplication
    Set oApp = ThisDrawing.Application
    Dim sAppName As String
    ' 注意：需要指定版本号（5.0）
    sAppName = "AeccXUiPipe.AeccPipeApplication.5.0"
    On Error Resume Next
    Set g_oPipeApplication = oApp.GetInterfaceObject(sAppName)
    On Error GoTo 0
    If (g_oPipeApplication Is Nothing) Then
        MsgBox "创建程序失败 " & sAppName & ", 退出."
        GetPipeObjects = False
        Exit Function
    End If
    Set g_oPipeDocument = g_oPipeApplication.ActiveDocument
    Set g_oPipeDatabase = g_oPipeDocument.Database
    GetPipeObjects = True
End Function

Attribute VB_Name = "PipeSetting"
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.

Option Explicit
''---------------------------------------------------------
'
'功能：获取管道设置
'
'作者：
'
'
'日期：２００７/０8
'
'
'修改记录：无
'
'
''-----------------------------------------------------------
Public Sub SetPipeSetting()

    If GetPipeObjects = False Then
        MsgBox "获取管道程序对象失败，退出"
        Exit Sub
    End If
    
    Dim oSettings As AeccPipeSettingsRoot
    Set oSettings = g_oPipeDocument.Settings

    ' 获取文档中缺省的管道规格设置
    With oSettings.PipeNetworkSettings.RulesSettings
    ThisDrawing.Utility.Prompt ("使用的管道规则:" + .PipeDefaultRules.Value + vbCrLf)
    End With
    ' 设置文档中管道的缺省单位
    With oSettings.PipeSettings.AmbientSettings
    .AngleSettings.Unit = aeccAngleUnitRadian
    .CoordinateSettings.Unit = aeccCoordinateUnitFoot
    .DistanceSettings.Unit = aeccCoordinateUnitFoot
    End With
    MsgBox ("设置文档中管道的缺省单位成功")

End Sub

Attribute VB_Name = "PipeStyle"

'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.

Option Explicit

''---------------------------------------------------------
'
'功能：创建或获取管道样式
'
'输入参数：sStyleName As String
'
'
'输出参数：AeccPipeStyle
'
'
'作者：
'
'
'日期：２００７/０8
'
'
'修改记录：无
'
'
''-----------------------------------------------------------

Public Function CreatePipeStyle(sStyleName As String) As AeccPipeStyle
    Dim oPipeStyle As AeccPipeStyle
    On Error Resume Next
    Set oPipeStyle = g_oPipeDocument.PipeStyles.Add(sStyleName)
    On Error GoTo 0
    If (oPipeStyle Is Nothing) Then
        On Error Resume Next
        Set oPipeStyle = g_oPipeDocument.PipeStyles.Item(sStyleName)
        On Error GoTo 0
        If (oPipeStyle Is Nothing) Then
            Set CreatePipeStyle = Nothing
            Exit Function
        End If
    End If
    
    ' 平面
    oPipeStyle.PlanOption.InnerDiameter = 2.1 '管道壁尺寸内径
    oPipeStyle.PlanOption.OuterDiameter = 2.4 '管道壁尺寸外径
    oPipeStyle.PlanOption.WallSizeType = aeccUserDefinedWallSize '用户定义
    oPipeStyle.PlanOption.WallSizeOptions = aeccPipeUseAbsoluteUnits
    oPipeStyle.PlanOption.EndLineSize = 2.1
    oPipeStyle.PlanOption.EndSizeType = aeccUserDefinedEndSize '用户定义
    oPipeStyle.PlanOption.EndSizeOptions = aeccPipeUseAbsoluteUnits '使用以绝对单位度量的大小

    ' 设定颜色
    oPipeStyle.DisplayStyle2d(aeccDispCompPlanPipeOutsideWall).color = 40 ' orange
    oPipeStyle.DisplayStyle2d(aeccDispCompPlanPipeInsideWall).color = 255 ' white
    oPipeStyle.DisplayStyle2d(aeccDispCompPlanPipeEndLine).color = 255 ' white
      
    ' 部件图案填充显示
    oPipeStyle.HatchStyle2d(aeccHatchPipePlan).Pattern = "DOTS"
    oPipeStyle.HatchStyle2d(aeccHatchPipePlan).HatchType = aeccHatchPreDefined
    oPipeStyle.HatchStyle2d(aeccHatchPipePlan).UseAngleOfObject = False
    oPipeStyle.HatchStyle2d(aeccHatchPipePlan).ScaleFactor = 9#
    oPipeStyle.PlanOption.HatchOptions = aeccHatchToInnerWalls
    oPipeStyle.DisplayStyle2d(aeccDispCompPlanPipeHatch).color = 40
    oPipeStyle.DisplayStyle2d(aeccDispCompPlanPipeHatch).Visible = True
    
    Set CreatePipeStyle = oPipeStyle
End Function



''---------------------------------------------------------
'
'功能：创建或获取结构样式
'
'输入参数：sStyleName As String
'
'
'输出参数：AeccStructureStyle
'
'
'作者：
'
'
'日期：２００７/０8
'
'
'修改记录：无
'
'
''-----------------------------------------------------------

'
Public Function CreateStructureStyle(sStyleName As String) As AeccStructureStyle
    Dim oStructureStyle As AeccStructureStyle
    On Error Resume Next
    Set oStructureStyle = g_oPipeDocument.StructureStyles.Add(sStyleName)
    On Error GoTo 0
    If (oStructureStyle Is Nothing) Then
        On Error Resume Next
        Set oStructureStyle = g_oPipeDocument.StructureStyles.Item(sStyleName)
        On Error GoTo 0
        If (oStructureStyle Is Nothing) Then
            Set CreateStructureStyle = Nothing
            Exit Function
        End If
    End If


    oStructureStyle.DisplayStyle2d(aeccDispCompPlanStructure).color = 30
    oStructureStyle.DisplayStyle2d(aeccDispCompPlanStructure).Visible = True
    
    oStructureStyle.PlanOption.MaskConnectedObjects = False
    oStructureStyle.PlanOption.SizeType = aeccStructureUseDrawingScale
    oStructureStyle.PlanOption.Size = 3.5

    oStructureStyle.DisplayStyle2d(aeccDispCompCrossSectionViewStructure).Visible = False
    oStructureStyle.DisplayStyle2d(aeccDispCompCrossSectionViewStructureHatch).Visible = False
    oStructureStyle.DisplayStyle2d(aeccDispCompPlanStructureHatch).Visible = False
    oStructureStyle.DisplayStyle2d(aeccDispCompProfileViewStructure).Visible = False
    oStructureStyle.DisplayStyle2d(aeccDispCompProfileViewStructureHatch).Visible = False
    oStructureStyle.DisplayStyle2d(aeccDispCompStructureModel3dSolid).Visible = False
    oStructureStyle.DisplayStyle2d(aeccDispStructureCompLast).Visible = False
    
    Set CreateStructureStyle = oStructureStyle
End Function ' CreateStructureStyle

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
Option Explicit


Public Sub PipeSample()
If GetPipeObjects = False Then

    MsgBox "获取管道程序，文档对象失败，退出"
    Exit Sub
End If

If CreatePipeNetwork = False Then
    MsgBox "创建管道失败，退出"
    Exit Sub
End If


CreatePipeNetwork
End Sub
