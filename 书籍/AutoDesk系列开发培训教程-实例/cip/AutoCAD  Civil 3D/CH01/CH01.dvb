Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.

'
Option Explicit
' 声明变量
Public g_oAeccApp As AeccApplication
Public g_oAeccDoc As AeccDocument
Public g_oAeccDb As AeccDatabase


'//--------------------------------------------
'   功能：获取Civil 3D程序、文档和数据库对象
'
'
'    作者：
'
'    日期： 2007-07
'
'//--------------------------------------------

Function GetCivilObjects() As Boolean
 ' 获取AeccApplication 对象.
    Dim oApp As AcadApplication
    Set oApp = ThisDrawing.Application
    ' 注意：需要指定版本号（5.0）.
    Const sAppName = "AeccXUiLand.AeccApplication.5.0"
    Set g_oAeccApp = oApp.GetInterfaceObject(sAppName)
    If (g_oAeccApp Is Nothing) Then
        MsgBox "Error creating " & sAppName & ", exit."
        GetCivilObjects = False
        Exit Function
    End If
    '获取文档和数据库对象
    Set g_oAeccDoc = g_oAeccApp.ActiveDocument
    Set g_oAeccDb = g_oAeccDoc.Database
    GetCivilObjects = True
End Function

'//--------------------------------------------
'   功能：子例程CH01，调用程序和文档对象
'
'
'    作者：
'
'    日期： 2007-07
'
'//--------------------------------------------
 Sub CH01()
    If GetCivilObjects = True Then
    
        MsgBox "获取Civil 3D的程序对象和文档对象" & vbCrLf & "当前文档的名称" & g_oAeccDoc.Name
    Else
        MsgBox "获取Civil 3D的程序对象和文档对象失败"
    End If
End Sub
