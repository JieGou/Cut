Attribute VB_Name = "Alignment"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit


''---------------------------------------------------------
'
'功能：基于Polyline创建路线
'
'作者：
'
'
'日期：２００７/０8
'
'
'修改记录：无
'
'
''-----------------------------------------------------------
Public Function CreateAlignmentsByLWPolyline() As Boolean
    Dim i As Integer

    ' 首先获取包含路线的站点
    If (CreateSite = False) Then
        CreateAlignmentsByLWPolyline = False
        Exit Function
    End If
    Dim oAlignments As AeccAlignments
    Set oAlignments = GetSite().Alignments
    


    ' 创建路线样式
    If (CreateAlignmentStyle("ALIGNMENT_STYLE_01") = False) Then
        CreateAlignmentsByLWPolyline = False
        Exit Function
    End If

    ' 创建路线标签样式
    If (CreateAlignmentLabelStyleSet("ALIGNMENT_LABEL_STYLE_SET_01") = False) Then
        CreateAlignmentsByLWPolyline = False
        Exit Function
    End If
    ' 创建多义线
    Dim oPoly As AcadLWPolyline
    Dim dPoints(0 To 5) As Double

    dPoints(0) = 0: dPoints(1) = 600
    dPoints(2) = 600: dPoints(3) = 0
    dPoints(4) = 1200: dPoints(5) = 600
    Set oPoly = g_oAeccDb.ModelSpace.AddLightWeightPolyline(dPoints)
    Dim dObjId As Long
    dObjId = oPoly.ObjectID
   
   ' 通过多义线创建路线
    Dim oAlignment As AeccAlignment
    Set oAlignment = oAlignments.AddFromPolyline("ALIGNMENT_01", "0", dObjId, _
        "ALIGNMENT_STYLE_01", "ALIGNMENT_LABEL_STYLE_SET_01", True, True)

    If (oAlignment Is Nothing) Then

       CreateAlignmentsByLWPolyline = False
        Exit Function
    End If
    
    ' 获取里程信息
    Dim oAStations As AeccAlignmentStations
    Set oAStations = oAlignment.GetStations(aeccAll, 30, 10)
    Debug.Print "# 里程数目: " & oAStations.Count
    
    g_oCivilApp.Update
    ThisDrawing.Application.ZoomExtents
    CreateAlignmentsByLWPolyline = True
End Function




''---------------------------------------------------------
'
'功能：创建直线
'
'作者：
'
'
'日期：２００７/０8
'
'
'修改记录：无
'
'
''-----------------------------------------------------------
Public Function CreateLine(x1 As Double, y1 As Double, z1 As Double, x2 As Double, y2 As Double, z2 As Double) As Long
    Dim oLine As AcadLine
    Dim dPoint1(2) As Double
    Dim dPoint2(2) As Double

    dPoint1(0) = x1: dPoint1(1) = y1: dPoint1(2) = z1
    dPoint2(0) = x2: dPoint2(1) = y2: dPoint2(2) = z2
    Set oLine = g_oAeccDb.ModelSpace.AddLine(dPoint1, dPoint2)
    CreateLine = oLine.ObjectID
End Function


'
' Creates an alignment based on layout data.
'

''---------------------------------------------------------
'
'功能：通过布局创建路线
'
'作者：
'
'
'日期：２００７/０8
'
'
'修改记录：无
'
'
''-----------------------------------------------------------
Public Function CreateAlignmentsByLayout() As Boolean
    Dim i As Integer
    
    ' 获取站点
    If (CreateSite = False) Then
        CreateAlignmentsByLayout = False
        Exit Function
    End If
    Dim oAlignments As AeccAlignments
    Set oAlignments = GetSite().Alignments

    ' 创建路线样式
    If (CreateAlignmentStyle("ALIGNMENT_STYLE_01") = False) Then
        CreateAlignmentsByLayout = False
        Exit Function
    End If

    ' 创建路线标签样式
    If (CreateAlignmentLabelStyleSet("ALIGNMENT_LABEL_STYLE_SET_01") = False) Then
        CreateAlignmentsByLayout = False
        Exit Function
    End If

    ' 创建路线
    Dim oAlignment As AeccAlignment
    Set oAlignment = oAlignments.Add("ALIGNMENT_02", "0", "ALIGNMENT_STYLE_01", "ALIGNMENT_LABEL_STYLE_SET_01")
    
    If (oAlignment Is Nothing) Then
        CreateAlignmentsByLayout = False
        Exit Function
    End If

    ' 添加实体到所创建路线中
    Dim point1(0 To 2) As Double
    Dim point2(0 To 2) As Double
    Dim point3(0 To 2) As Double
    point1(0) = 200: point1(1) = 800: point1(2) = 0
    point2(0) = 600: point2(1) = 400: point2(2) = 0
    point3(0) = 1000: point3(1) = 800: point3(2) = 0
    
    Dim oAlignmentTangent As AeccAlignmentTangent
    Set oAlignmentTangent = oAlignment.Entities.AddFixedLine1(point1, point2)
    Dim oAlignmentArc As AeccAlignmentArc
    Set oAlignmentArc = oAlignment.Entities.AddFloatingCurve6(oAlignmentTangent.Id, point3)

    ' 设置设计速度
    Dim oDesignSpeed As AeccDesignSpeed
    '从里程K0 + 000.00起
    Set oDesignSpeed = oAlignment.DesignSpeeds.Add(0#) ' Station 0 + 00.00
    oDesignSpeed.Value = 45
    oDesignSpeed.Comment = "Straightaway"
    ' 从里程K0 +030.00起
    Set oDesignSpeed = oAlignment.DesignSpeeds.Add(430#) ' Station 4 + 30.00
    oDesignSpeed.Value = 30
    oDesignSpeed.Comment = "Start of curve"
    ' 从里程K1 + 427.131起直到终点
    Set oDesignSpeed = oAlignment.DesignSpeeds.Add(1427.131) ' Station 14 + 27.131
    oDesignSpeed.Value = 35
    oDesignSpeed.Comment = "End of curve"

    ' 如果希望每隔100个图形单位设置主桩号、每隔20个单位设置次桩号

    Dim oAlignmentStations As AeccAlignmentStations
    Set oAlignmentStations = oAlignment.GetStations(aeccAll, 100#, 20#)
    Debug.Print "# 里程数目: " & oAlignmentStations.Count
    
    For i = 0 To oAlignmentStations.Count - 1
    If (oAlignmentStations.Item(i).Type = aeccMajor) Then
            Dim j As Integer
            Dim x As Integer
            Dim y As Integer
            j = oAlignmentStations.Item(i).Station
            x = oAlignmentStations.Item(i).Easting
            y = oAlignmentStations.Item(i).Northing
            Debug.Print "里程 " & j & " 位于: " & x & ", " & y
        End If
    Next i
    
    ' 用断链调整路线里程
    Dim oStationEquation As AeccStationEquation
    ' 修改一条路线的里程，将原始里程为80的那个点修改为720的新里程，并设置后续里程递加
    Set oStationEquation = oAlignment.StationEquations.Add(80, 0, 720, aeccIncreasing)
    Set oAlignmentStations = oAlignment.GetStations(aeccEquation, 180#, 0#)
    For i = 0 To oAlignmentStations.Count - 1
        Debug.Print "里程 "; oAlignmentStations.Item(i).Station; " 位于: "; oAlignmentStations.Item(i).Easting; ", "; oAlignmentStations.Item(i).Northing
    Next i

    
    ' 给出东距和北距，获取临近的里程，然后平移至指定点并绘制直线
    Dim dStation As Double
    Dim dOffset As Double
    Dim dNorth As Double
    Dim dEast As Double
    oAlignment.StationOffset 600, 600, dStation, dOffset
    Debug.Print "距离 600,600最近的里程位于: "; dStation; " ，经过平移: "; dOffset
    Debug.Print
    oAlignment.PointLocation dStation, 0#, dEast, dNorth
    Call CreateLine(600, 600, 0#, dEast, dNorth, 0#)
    
    ' 平移路线
    oAlignment.Offset 10.5
    oAlignment.Offset -10.5

   
    '''''''''''''''''''''''''''''''''''''''''''''''''''''''''''
    ' 设置超高
    Dim oSuperElevationData As AeccSuperElevationData
    Dim oSuperElevationElem As AeccSuperElevationDataElem

    ' 在K1+100.0的位置处创建一个超高要素, 为oSuperElevationElem变量指定一个新的默认超高数据

    Set oSuperElevationData = oAlignment.SuperelevationData
    oSuperElevationData.Add 1100, oSuperElevationElem

    oSuperElevationElem.SegmentCrossSlope(aeccSuperLeftOutShoulderCrossSlope) = 0.05
    oSuperElevationElem.SegmentCrossSlope(aeccSuperLeftOutLaneCrossSlope) = 0.02
    oSuperElevationElem.SegmentCrossSlope(aeccSuperLeftInLaneCrossSlope) = 0.01
    oSuperElevationElem.SegmentCrossSlope(aeccSuperLeftInShoulderCrossSlope) = 0.03
    oSuperElevationElem.SegmentCrossSlope(aeccSuperRightInShoulderCrossSlope) = 0.03
    oSuperElevationElem.SegmentCrossSlope(aeccSuperRightInLaneCrossSlope) = 0.01
    oSuperElevationElem.SegmentCrossSlope(aeccSuperRightOutLaneCrossSlope) = 0.02
    oSuperElevationElem.SegmentCrossSlope(aeccSuperRightOutShoulderCrossSlope) = 0.05
    oSuperElevationElem.TransPointType = aeccSuperManual
    oSuperElevationElem.TransPointDesc = "Manual adjustment"
    oSuperElevationElem.RawStation = 1100

    '
    g_oCivilApp.Update
    ThisDrawing.Application.ZoomExtents
    CreateAlignmentsByLayout = True
End Function

Attribute VB_Name = "AlignmentStyle"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit


'
' Create an alignment style with the given name,
' if no such style already exists.
'

''---------------------------------------------------------
'
'功能：创建路线样式
'
'作者：
'
'
'日期：２００７/０8
'
'
'修改记录：无
'
'
''-----------------------------------------------------------
Function CreateAlignmentStyle(sStyleName As String) As Boolean
    ' Make a new alignment style for our alignment if it
    ' has not been made already.  If there is a problem
    ' making the new style there is an error, so we trap
    ' that.
    Dim oAlignmentStyle As AeccAlignmentStyle
    
    ' See if a style by this name already exists.  If it
    ' does, we will use that style.
    On Error Resume Next
    Set oAlignmentStyle = g_oDocument.AlignmentStyles.Item(sStyleName)
    On Error GoTo 0
    ' If it does not, create a new alignment style by
    ' that name.
    If (oAlignmentStyle Is Nothing) Then
        On Error Resume Next
        Set oAlignmentStyle = g_oDocument.AlignmentStyles.Add(sStyleName)
        On Error GoTo 0
        If (oAlignmentStyle Is Nothing) Then
            MsgBox "Error setting an Alignment Style: " & Err.Description
            Err.Clear
            CreateAlignmentStyle = False
        End If
    End If
    
    ' Do not show direction arrows.  Styles do not govern
    ' the size of direction arrows - that is done in the
    ' ambient settings.
    oAlignmentStyle.ArrowDisplayStyle2d.Visible = False
    oAlignmentStyle.ArrowDisplayStyle3d.Visible = False
    ' Display curves using violet.
    oAlignmentStyle.CurveDisplayStyle2d.color = 200 ' violet
    oAlignmentStyle.CurveDisplayStyle3d.color = 200 ' violet
    oAlignmentStyle.CurveDisplayStyle2d.Visible = True
    oAlignmentStyle.CurveDisplayStyle3d.Visible = True
    ' Display straight sections in blue.
    oAlignmentStyle.LineDisplayStyle2d.color = 160 ' blue
    oAlignmentStyle.LineDisplayStyle3d.color = 160 ' blue
    oAlignmentStyle.LineDisplayStyle2d.Visible = True
    oAlignmentStyle.LineDisplayStyle3d.Visible = True

    oAlignmentStyle.EnableRadiusSnap = True
    
    g_oCivilApp.Update
    CreateAlignmentStyle = True
End Function

'
''---------------------------------------------------------
'
'功能：创建路线标签样式
'
'作者：
'
'
'日期：２００７/０8
'
'
'修改记录：无
'
'
''-----------------------------------------------------------
Public Function CreateAlignmentLabelStyleSet(sLabelStyleSetName As String) As Boolean
    Dim i As Integer
    
    ' Add a new AeccAlignmentLabelStyleSet in the document's
    ' collection of AlignmentStyleSet objects, after first
    ' deleting any older version of the style set that might
    ' exist.
    Dim oAlignmentLabelStyleSet As AeccAlignmentLabelStyleSet
    Set oAlignmentLabelStyleSet = Nothing
    On Error Resume Next
    g_oDocument.AlignmentLabelStyleSets.Remove (sLabelStyleSetName)
    
    ' If there is an object using this style set, then it cannot
    ' be removed.  To cover those cases, we will just try using
    ' that style.
    Set oAlignmentLabelStyleSet = g_oDocument.AlignmentLabelStyleSets.Item(sLabelStyleSetName)
    On Error GoTo 0
    If (oAlignmentLabelStyleSet Is Nothing) Then
        Set oAlignmentLabelStyleSet = g_oDocument.AlignmentLabelStyleSets.Add(sLabelStyleSetName)
    Else
        ' Using the old style.  No need to make a new one.
        CreateAlignmentLabelStyleSet = True
        Exit Function
    End If
    
    ' Assign some alignment label styles.
    oAlignmentLabelStyleSet.Description = "This demonstrates many design elements."
    
    ' -------------------------------------------------------
    ' This section demonstrates how to set the major station
    ' label styles.  Minor station labels and geometry point
    ' labels are similarly structured.

    Dim oMajorStationStyle As AeccLabelMajorStationStyleSetItem
    Dim oLabelStyle As AeccLabelStyle
    Dim oLabelStyleTickComponent As AeccLabelStyleTickComponent
    Dim oLabelStyleLineComponent As AeccLabelStyleLineComponent
    Dim oLabelStyleTextComponent As AeccLabelStyleTextComponent
    Dim oLabelStyleBlockComponent As AeccLabelStyleBlockComponent

    ' Add to the document a generic AeccLabelStyle object for
    ' managing the style of major station labels.
    On Error Resume Next
    g_oDocument.AlignmentLabelStyles.MajorStationLabelStyles.Remove "Parallel with Line, Tick and Speed"
    Set oLabelStyle = g_oDocument.AlignmentLabelStyles.MajorStationLabelStyles.Item("Parallel with Line, Tick and Speed")
    On Error GoTo 0
    If (oLabelStyle Is Nothing) Then
        Set oLabelStyle = g_oDocument.AlignmentLabelStyles.MajorStationLabelStyles.Add("Parallel with Line, Tick and Speed")
    End If
    
    ' Add to the AeccLabelStyle object an object for managing
    ' the style of label ticks.  This style governs the
    ' properties of the tick mark placed at regular intervals
    ' (in this case, at every station).
    On Error Resume Next
    oLabelStyle.TickComponents.Remove "New Tick"
    Set oLabelStyleTickComponent = oLabelStyle.TickComponents.Item("New Tick")
    On Error GoTo 0
    If (oLabelStyleTickComponent Is Nothing) Then
        Set oLabelStyleTickComponent = oLabelStyle.TickComponents.Add("New Tick")
    End If
    ' Specify what kind of symbol is used for the tick.
    'ReadOnly Property
    'oLabelStyleTickComponent.BlockName = "AeccTickLine"
    oLabelStyleTickComponent.Lineweight.Value = 60 ' .60 mm
    oLabelStyleTickComponent.AlignWithObject = True ' perpendicular to alignment
    oLabelStyleTickComponent.Angle = 0# ' in degrees
    oLabelStyleTickComponent.Visibility = True

    ' Add to the AeccLabelStyle object an object for managing
    ' the style of label blocks.  This style governs arbitrary
    ' symbols.  We will use this to add a circular tick mark
    ' around the current line tick mark.
    On Error Resume Next
    oLabelStyle.BlockComponents.Remove "New Block"
    Set oLabelStyleBlockComponent = oLabelStyle.BlockComponents.Item("New Block")
    On Error GoTo 0
    If (oLabelStyleBlockComponent Is Nothing) Then
        Set oLabelStyleBlockComponent = oLabelStyle.BlockComponents.Add("New Block")
    End If
    'ReadOnly Property
    'oLabelStyleBlockComponent.BlockName = "AeccTickCircle"
    oLabelStyleBlockComponent.Visibility = True
    
    ' Add to the AeccLabelStyle object an object for managing
    ' the style of label lines.  This style governs lines placed
    ' at each station.  We will use this to point out which
    ' station each distantly located text label belongs to.
    On Error Resume Next
    oLabelStyle.LineComponents.Remove "New Line"
    Set oLabelStyleLineComponent = oLabelStyle.LineComponents.Item("New Line")
    On Error GoTo 0
    If (oLabelStyleLineComponent Is Nothing) Then
        Set oLabelStyleLineComponent = oLabelStyle.LineComponents.Add("New Line")
    End If
    oLabelStyleLineComponent.color = 40 ' orange-yellow
    oLabelStyleLineComponent.Angle = 2.094 ' radians, = 120 degrees
    oLabelStyleLineComponent.Length = 0.015 ' in whatever units are used in the drawing
    oLabelStyleLineComponent.StartPointXOffset = 0.005
    oLabelStyleLineComponent.StartPointYOffset = -0.005
    oLabelStyleLineComponent.Visibility = True
    
    ' Text componets specify what text is displayed at each station
    ' and managing how that text looks.  We will change what text is
    ' displayed, and move it under and to the side of each station
    ' anchor.
    
    ' Try using an already existing text component, as default
    ' label styles usually have one.
    On Error Resume Next
    Set oLabelStyleTextComponent = oLabelStyle.TextComponents.Item(0)
    On Error GoTo 0
    ' If a text component does not exist we will make a new one.
    If (oLabelStyleTextComponent Is Nothing) Then
        Set oLabelStyleTextComponent = oLabelStyle.TextComponents.Add("New Text")
    End If
    ' Curve the text to follow the curves of the alignment.
    oLabelStyleTextComponent.AllowToCurve = True
    oLabelStyleTextComponent.XOffset = 0.01
    oLabelStyleTextComponent.YOffset = -0.025 - oLabelStyleTextComponent.Height
    oLabelStyleTextComponent.Contents = "SPD=<[Design Speed(P0|RN|AP|Sn|OF)]>  STA=<[Station Value(Uft|FS|P2|RN|AP|Sn|TP|B2|EN|W0|OF)]>"
    oLabelStyleTextComponent.color = 253 ' light grey

    ' We have just finished adding a tick, a block, and a line
    ' to the AeccLabelStyle object, as well as modifying its
    ' text.  Now we will add the AeccLabelStyle object to the
    ' MajorStationLabelStyleSet, which is one of the style sets
    ' governing how the alignment is labeled.
    
    ' This specifies the distance along the alignment (in whatever
    ' units the drawing is using) to place each station.
    Dim dIncrement As Double
    dIncrement = 260#
    
    Set oMajorStationStyle = oAlignmentLabelStyleSet.MajorStationLabelStyleSet.Add(oLabelStyle, dIncrement)
    
    ' End of setting the major station label style.
    ' -------------------------------------------------------

    CreateAlignmentLabelStyleSet = True
End Function ' CreateAlignmentLabelStyleSet

Attribute VB_Name = "BaseObjects"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' 声明全局的程序、文档和数据库对象
Public g_oCivilApp As AeccApplication
Public g_oDocument As AeccDocument
Public g_oAeccDb As AeccDatabase


''---------------------------------------------------------
'
'功能：获取模块的程序、文档和数据库对象
'
'作者：
'
'
'日期：２００７/０8
'
'
'修改记录：无
'
'
''-----------------------------------------------------------
Public Function GetBaseCivilObjects() As Boolean
    Dim oApp As AcadApplication
    Set oApp = ThisDrawing.Application
    '需要指定版本号（5.0）.
    Const sAppName = "AeccXUiLand.AeccApplication.5.0"
    Set g_oCivilApp = oApp.GetInterfaceObject(sAppName)
    If g_oCivilApp Is Nothing Then
        MsgBox "获取程序对象 " & sAppName & "错误, 退出."
        GetBaseCivilObjects = False
        Exit Function
    End If
    Set g_oDocument = g_oCivilApp.ActiveDocument
    Set g_oAeccDb = g_oDocument.Database
    GetBaseCivilObjects = True
End Function

Attribute VB_Name = "Site"

'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit


''---------------------------------------------------------
'
'功能：创建站点
'
'作者：
'
'
'日期：２００７/０8
'
'
'修改记录：无
'
'
''-----------------------------------------------------------
Public Function CreateSite() As Boolean
    Dim oSites As AeccSites
    Set oSites = g_oDocument.Sites
    Dim oSite As AeccSite
    
    ' 如果站点已经存在，则直接获取之
    On Error Resume Next
    Set oSite = oSites.Item("Site_01")
    On Error GoTo 0
    If (oSite Is Nothing) Then
        Set oSite = oSites.Add("Site_01")
        If (oSite Is Nothing) Then
            Debug.Print "创建站点失败"
            CreateSite = False
            Exit Function
        End If
    End If
    CreateSite = True
End Function


'
' Return the a site object with the name that we use for all
' sites in this application.  If such a site does not exist,
' return Nothing.
'

''---------------------------------------------------------
'
'功能：创建指定的站点
'
'作者：
'
'
'日期：２００７/０8
'
'
'修改记录：无
'
'
''-----------------------------------------------------------
Public Function GetSite() As AeccSite
    On Error Resume Next
    Set GetSite = g_oDocument.Sites.Item("Site_01")
    On Error GoTo 0

    If (GetSite Is Nothing) Then
        Debug.Print "访问站点 Site_01 失败."
        GetSite = Nothing
        Exit Function
    End If
End Function

Attribute VB_Name = "Subroutines"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
'
Option Explicit
'

''---------------------------------------------------------
'
'功能：基于Polyline创建路线
'
'作者：
'
'
'日期：２００７/０8
'
'
'修改记录：无
'
'
''-----------------------------------------------------------


Sub AlignmentFromPolyline()
    'always get the objects again since MDI is supported
    If (GetBaseCivilObjects = False) Then
        Exit Sub
    End If
    
    If (CreateAlignmentsByLWPolyline = False) Then
        Debug.Print "Error creating alignment object."
        Exit Sub
    End If
    
    g_oCivilApp.Update
End Sub

''---------------------------------------------------------
'
'功能：基于布局创建路线
'
'作者：
'
'
'日期：２００７/０8
'
'
'修改记录：无
'
'
''-----------------------------------------------------------
Sub AlignmentFromLayout()
    '获取程序和文档等对象
    If (GetBaseCivilObjects = False) Then
        Exit Sub
    End If
    
    If (CreateAlignmentsByLayout = False) Then
        Debug.Print "Error creating alignment object."
        Exit Sub
    End If
    
    g_oCivilApp.Update
End Sub
