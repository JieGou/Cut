Attribute VB_Name = "BaseObjects"
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' 声明全局的程序、文档和数据库对象
Public g_oCivilApp As AeccApplication
Public g_oDocument As AeccDocument
Public g_oAeccDb As AeccDatabase


''---------------------------------------------------------
'
'功能：获取模块的程序、文档和数据库对象
'
'作者：
'
'
'日期：２００７/０8
'
'
'修改记录：无
'
'
''-----------------------------------------------------------
Public Function GetBaseCivilObjects() As Boolean
    Dim oApp As AcadApplication
    Set oApp = ThisDrawing.Application
    '需要指定版本号（5.0）.
    Const sAppName = "AeccXUiLand.AeccApplication.5.0"
    Set g_oCivilApp = oApp.GetInterfaceObject(sAppName)
    If g_oCivilApp Is Nothing Then
        MsgBox "获取程序对象 " & sAppName & "错误, 退出."
        GetBaseCivilObjects = False
        Exit Function
    End If
    Set g_oDocument = g_oCivilApp.ActiveDocument
    Set g_oAeccDb = g_oDocument.Database
    GetBaseCivilObjects = True
End Function

Attribute VB_Name = "SampleLine"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'''---------------------------------------------------------
'
'功能：向路线上添加采样线组（带有定制的样式和标签样式）
'
'作者：
'
'
'日期：２００７/０8
'
'
'修改记录：无
'
'
''-----------------------------------------------------------
Public Function CreateSampleLineGroup(oAlignment As AeccAlignment) As Boolean
    ' 获取路线的采样线组集合
    Dim oSampleLineGroups As AeccSampleLineGroups
    On Error Resume Next
    Set oSampleLineGroups = oAlignment.SampleLineGroups
    On Error GoTo 0
    If (oSampleLineGroups Is Nothing) Then
        Debug.Print "获取路线的采样线组集合失败，退出"
        CreateSampleLineGroup = False
        Exit Function
    End If

    ' 创建采样线组使用的打印样式
    Dim oGroupPlotStyle As AeccGroupPlotStyle
    If (CreateGroupPlotStyle("Group plot style 01") = False) Then
        MsgBox "创建采样线组使用的打印样式失败"
        CreateSampleLineGroup = False
        Exit Function
    End If
    Set oGroupPlotStyle = g_oDocument.GroupPlotStyles.Item("Group plot style 01")

    ' 创建采样线组使用的样式
    Dim oSampleLineStyle As AeccSampleLineStyle
    If (CreateSampleLineStyle("Sample Line style 01") = False) Then
        MsgBox "创建采样线组使用的样式失败"
        CreateSampleLineGroup = False
        Exit Function
    End If
    Set oSampleLineStyle = g_oDocument.SampleLineStyles.Item("Sample Line style 01")

    ' 创建采样线组使用的标签样式
    Dim oSampleLineLabelStyle As AeccLabelStyle
    If (CreateSampleLineLabelStyle("Sample Line label style 01") = False) Then
        MsgBox "创建采样线组使用的标签样式失败."
        CreateSampleLineGroup = False
        Exit Function
    End If
    Set oSampleLineLabelStyle = g_oDocument.SampleLineLabelStyles.Item("Sample Line label style 01")


    ' 创建一个现的采样线组
    Dim oSampleLineGroup As AeccSampleLineGroup
    Set oSampleLineGroup = oSampleLineGroups.Add("Sample Line group 01", "0", oGroupPlotStyle, oSampleLineStyle, oSampleLineLabelStyle)
    
    ' 添加曲面到采样线组
    Dim oSectionStyle As AeccSectionStyle
    ' 创建横断面样式
    If (CreateSectionStyle("Sample Line section style 01") = False) Then
        MsgBox "创建横断面样式失败."
        CreateSampleLineGroup = False
        Exit Function
    End If
    Set oSectionStyle = g_oDocument.SectionStyles.Item(0)
    
    Dim oSampledSurface As AeccSampledSurface
    Set oSampledSurface = oSampleLineGroup.SampledSurfaces.Add(g_oDocument.Surfaces.Item(0), oSectionStyle)
    oSampledSurface.UpdateMode = aeccSectionStateDynamic
    ' 注意: 如果没有设置成True,横断面将不能从采样线创建
    oSampledSurface.Sample = True
    
    ''''''''''''''''''''''''''''''''''''''''''''''''''''''
    ' 可以使用以下三种方法创建采样线
    
    
    ' (1) 基于AutoCAD多段线创建采样线
    Dim oPoly As AcadLWPolyline
    Dim dPoints(0 To 3) As Double

    dPoints(0) = 4750: dPoints(1) = 4050
    dPoints(2) = 4770: dPoints(3) = 3950
    Set oPoly = ThisDrawing.ModelSpace.AddLightWeightPolyline(dPoints)
    Call oSampleLineGroup.SampleLines.AddByPolyline("Sample Line 01", oPoly, True)
    
    
    ' (2) 基于里程创建采样线
    Dim dSwathWidthLeft As Double
    Dim dSwathWidthRight As Double
    Dim dStation As Double
    dSwathWidthRight = 45.5
    dSwathWidthLeft = 35.5
    dStation = 1100.5
    Call oSampleLineGroup.SampleLines.AddByStation("Sample Line 02", dStation, dSwathWidthLeft, dSwathWidthRight)
    
    ' (3) 指定绘制采样线的位置
    Dim oStationRange As New AeccStationRange
    oStationRange.UseSampleIncrements = True
    oStationRange.SampleAtHighLowPoints = False
    oStationRange.SampleAtHorizontalGeometryPoints = False
    oStationRange.SampleAtSuperelevationCriticalStations = False
    oStationRange.SampleAtRangeEnd = True
    oStationRange.SampleAtRangeStart = True
    oStationRange.StartRangeAtAlignmentStart = False
    oStationRange.EndRangeAtAlignmentEnd = False
    oStationRange.StartRange = 10#
    '仅在1000个单位的长度范围内进行采样
    oStationRange.EndRange = 1010#
    ' 沿着直线每隔200个单位采样一次
    oStationRange.IncrementTangent = 200#
    ' 沿着曲线每隔50个单位采样一次
    oStationRange.IncrementCurve = 50#
    '  沿着缓和曲线每隔50个单位采样一次
    oStationRange.IncrementSpiral = 50#
    
     '里程点两侧采集宽度为50个单位
    oStationRange.SwathWidthLeft = 50#
    oStationRange.SwathWidthRight = 50#
    oStationRange.SampleLineDefaultDirection = aeccDirectionFromBaseAlignment
    Set oStationRange.SampleLineStyle = oSampleLineStyle
    
    ' 可以指定里程的范围，按照相同的设置创建一系列的采样线
    oSampleLineGroup.SampleLines.AddByStationRange "Sample Line 03", aeccSampleLineDuplicateActionOverwrite, oStationRange

   
    CreateSampleLineGroup = True
End Function ' CreateSampleLineGroup

Attribute VB_Name = "SampleLineStyle"
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit



'''---------------------------------------------------------
'
'功能：创建采样线组打印样式
'
'作者：
'
'
'日期：２００７/０8
'
'
'修改记录：无
'
'
''-----------------------------------------------------------
Public Function CreateGroupPlotStyle(sStyleName As String) As Boolean
    ' Create a new group plot style and add it to the
    ' drawing's collection of such styles.
    Dim oGroupPlotStyle As AeccGroupPlotStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.GroupPlotStyles.Remove (sStyleName)
    Set oGroupPlotStyle = g_oDocument.GroupPlotStyles.Item(sStyleName)
    On Error GoTo 0
    If (oGroupPlotStyle Is Nothing) Then
        On Error Resume Next
        Set oGroupPlotStyle = g_oDocument.GroupPlotStyles.Add(sStyleName)
        On Error GoTo 0
        If (oGroupPlotStyle Is Nothing) Then
            Debug.Print "Error creating an group plot style"
            CreateGroupPlotStyle = False
            Exit Function
        End If
    End If
    
    oGroupPlotStyle.AlignSectionViewsAbout = aeccGroupPlotAlignViewCenterLine
    oGroupPlotStyle.CellSize = aeccGroupPlotCellSizeUniform
    oGroupPlotStyle.GapBetweenPages = 1#
    'oGroupPlotStyle.MajorHorizontalGridRowSpace = 20.5
    'oGroupPlotStyle.MajorVerticalGridColumnSpace = 20.5
    oGroupPlotStyle.PlotBy = aeccGroupPlotAreaAll
    oGroupPlotStyle.PlotSectionViewsBy = aeccGroupPlotByRows
    oGroupPlotStyle.MaximumInRow = 18
    oGroupPlotStyle.StartCorner = aeccGroupPlotCornerUpperLeft
    
    ' ------------------------------------------------
    ' In this section, we will make a new sheet style.
    
    ' Create a new sheet style and add it to the drawing's
    ' collection of such styles.
    Dim oSheetStyle As AeccSheetStyle
    On Error Resume Next
    g_oDocument.SheetStyles.Remove ("Sheet Style 01")
    Set oSheetStyle = g_oDocument.SheetStyles.Item("Sheet Style 01")
    On Error GoTo 0
    If (oSheetStyle Is Nothing) Then
        On Error Resume Next
        Set oSheetStyle = g_oDocument.SheetStyles.Add("Sheet Style 01")
        On Error GoTo 0
        If (oSheetStyle Is Nothing) Then
            Debug.Print "Error creating a sheet style"
            CreateGroupPlotStyle = False
            Exit Function
        End If
    End If
    
    ' Set the sheet style properties.
    oSheetStyle.SheetBorderDisplayStyle2d.color = 170 ' blue
    oSheetStyle.MajorHorizontalGridDisplayStyle2d.color = 170 ' blue
    'oSheetStyle.MajorHorizontalGridSize = 25.5
    
    ' Finished making a new sheet style.
    ' ------------------------------------------------
    
    ' Assign out sheet style to the group plot style.
    oGroupPlotStyle.SheetStyle = oSheetStyle.Name
    
    CreateGroupPlotStyle = True
End Function ' CreateGroupPlotStyle



'''---------------------------------------------------------
'
'功能：创建采样线样式
'
'作者：
'
'
'日期：２００７/０8
'
'
'修改记录：无
'
'
''-----------------------------------------------------------
'
Public Function CreateSampleLineStyle(sStyleName As String) As Boolean
    ' Create a new sample line style and add it to the
    ' drawing's collection of such styles.
    Dim oSampleLineStyle As AeccSampleLineStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SampleLineStyles.Remove (sStyleName)
    Set oSampleLineStyle = g_oDocument.SampleLineStyles.Item(sStyleName)
    On Error GoTo 0
    If (oSampleLineStyle Is Nothing) Then
        On Error Resume Next
        Set oSampleLineStyle = g_oDocument.SampleLineStyles.Add(sStyleName)
        On Error GoTo 0
        If (oSampleLineStyle Is Nothing) Then
            Debug.Print "Error creating an sample line style"
            CreateSampleLineStyle = False
            Exit Function
        End If
    End If

    oSampleLineStyle.VerticesDisplayStyle2d.color = 220 ' pink
    oSampleLineStyle.LineDisplayStyle2d.color = 60 ' yellow-green
    
    CreateSampleLineStyle = True
End Function ' CreateSampleLineStyle



'''---------------------------------------------------------
'
'功能：创建采样线标签样式
'
'作者：
'
'
'日期：２００７/０8
'
'
'修改记录：无
'
'
''-----------------------------------------------------------
Public Function CreateSampleLineLabelStyle(sStyleName As String) As Boolean
    ' Create a new sample line style and add it to the
    ' drawing's collection of such styles.
    Dim oOffsetLabelStyle As AeccLabelStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SampleLineLabelStyles.Remove (sStyleName)
    Set oOffsetLabelStyle = g_oDocument.SampleLineLabelStyles.Item(sStyleName)
    On Error GoTo 0
    If (oOffsetLabelStyle Is Nothing) Then
        On Error Resume Next
        Set oOffsetLabelStyle = g_oDocument.SampleLineLabelStyles.Add(sStyleName)
        On Error GoTo 0
        If (oOffsetLabelStyle Is Nothing) Then
            Debug.Print "Error creating an sample line style"
            CreateSampleLineLabelStyle = False
            Exit Function
        End If
    End If

    ' -------------------------------------------------------
    ' This section demonstrates how to set the major station
    ' label styles.  Minor offset labels, grade break labels,
    ' and segment labels are similarly structured.

    Dim oLabelStyleTickComponent As AeccLabelStyleTickComponent
    Dim oLabelStyleLineComponent As AeccLabelStyleLineComponent
    Dim oLabelStyleTextComponent As AeccLabelStyleTextComponent
    Dim oLabelStyleBlockComponent As AeccLabelStyleBlockComponent

    ' Add to the AeccLabelStyle object an object for managing
    ' the style of label ticks.  This style governs the
    ' properties of the tick mark placed at regular intervals
    ' (in this case, at every station).
    On Error Resume Next
    oOffsetLabelStyle.TickComponents.Remove "Sample tick 01"
    Set oLabelStyleTickComponent = oOffsetLabelStyle.TickComponents.Item("Sample tick 01")
    On Error GoTo 0
    If (oLabelStyleTickComponent Is Nothing) Then
        Set oLabelStyleTickComponent = oOffsetLabelStyle.TickComponents.Add("Sample tick 01")
    End If
    ' Specify what kind of symbol is used for the tick.
    'oLabelStyleTickComponent.BlockName = "AeccTickLine"
    oLabelStyleTickComponent.Lineweight.Value = 60 ' .60 mm
    oLabelStyleTickComponent.AlignWithObject = True ' perpendicular to alignment
    oLabelStyleTickComponent.Angle = 0# ' in degrees
    oLabelStyleTickComponent.Visibility = True

    ' Add to the AeccLabelStyle object an object for managing
    ' the style of label blocks.  This style governs arbitrary
    ' symbols.  We will use this to add a circular tick mark
    ' around the current line tick mark.
    On Error Resume Next
    oOffsetLabelStyle.BlockComponents.Remove "Sample block 01"
    Set oLabelStyleBlockComponent = oOffsetLabelStyle.BlockComponents.Item("Sample block 01")
    On Error GoTo 0
    If (oLabelStyleBlockComponent Is Nothing) Then
        Set oLabelStyleBlockComponent = oOffsetLabelStyle.BlockComponents.Add("Sample block 01")
    End If
    'oLabelStyleBlockComponent.BlockName = "AeccTickCircle"
    oLabelStyleBlockComponent.Visibility = True
    
    ' Add to the AeccLabelStyle object an object for managing
    ' the style of label lines.  This style governs lines placed
    ' at each station.  We will use this to point out which
    ' station each distantly located text label belongs to.
    On Error Resume Next
    oOffsetLabelStyle.LineComponents.Remove "Sample line 01"
    Set oLabelStyleLineComponent = oOffsetLabelStyle.LineComponents.Item("Sample line 01")
    On Error GoTo 0
    If (oLabelStyleLineComponent Is Nothing) Then
        Set oLabelStyleLineComponent = oOffsetLabelStyle.LineComponents.Add("Sample line 01")
    End If
    oLabelStyleLineComponent.color = 40 ' orange-yellow
    oLabelStyleLineComponent.Angle = 2.094 ' radians, = 120 degrees
    oLabelStyleLineComponent.Length = 0.015 ' in whatever units are used in the drawing
    oLabelStyleLineComponent.StartPointXOffset = 0.0005
    oLabelStyleLineComponent.StartPointYOffset = 0
    oLabelStyleLineComponent.Visibility = True
    
    ' The major station label style automatically comes with a
    ' TextComponent named "Station".  Text componets like this
    ' one are for specifying what text is displayed at each
    ' station, and for managing how that text looks.  We will
    ' change what text is displayed, and move it under and to
    ' the side of each station anchor.
    Set oLabelStyleTextComponent = oOffsetLabelStyle.TextComponents.Item(0)
    ' Curve the text to follow the curves of the alignment.
    oLabelStyleTextComponent.AllowToCurve = True
    oLabelStyleTextComponent.XOffset = 0.01
    oLabelStyleTextComponent.YOffset = -0.015 - oLabelStyleTextComponent.Height
    oLabelStyleTextComponent.Contents = "Sta=<[Sample Line Raw Station(Uft|FS|P2|RN|AP|Sn|TP|B2|EN|W0|OF)]>"
    oLabelStyleTextComponent.color = 253 ' light grey

    ' We have just finished adding a tick, a block, and a line
    ' to the AeccLabelStyle object, as well as modifying its
    ' text.  Now we will add the AeccLabelStyle object to the
    ' MajorStationLabelStyleSet, which is one of the style sets
    ' governing how the alignment is labeled.
    'Debug.Print "count MajorStationLabelStyleSet: "; oAlignmentLabelStyleSet.MajorStationLabelStyleSet.Count
    'For i = 0 To oAlignmentLabelStyleSet.MajorStationLabelStyleSet.Count - 1
    '    If (oAlignmentLabelStyleSet.MajorStationLabelStyleSet.Item(i).Style.Name = oLabelStyle.Name) Then
    '        oAlignmentLabelStyleSet.MajorStationLabelStyleSet.Remove i
    '    End If
    'Next i
    'Dim dIncrement As Double
    '' This specifies the distance along the alignment (in whatever
    '' units the drawing is using) to place each station.
    'dIncrement = 900#
    '
    'Set oMajorStationStyle = oSampleLineLabelStyle.MajorStationLabelStyleSet.Add(oLabelStyle, dIncrement)
    'Set oMajorStationStyle = oAlignmentLabelStyleSet.MajorStationLabelStyleSet.Add(oLabelStyle, dIncrement)
    ' End of setting the major station label style.
    ' -------------------------------------------------------
    
    ' Set the default values for the style.
    g_oDocument.SampleLineLabelStyles.LabelStyleDefaults.LabelProperties.Visibility = True
    
    CreateSampleLineLabelStyle = True
End Function ' CreateSampleLineLabelStyle

'''---------------------------------------------------------
'
'功能：创建横断面样式
'
'作者：
'
'
'日期：２００７/０8
'
'
'修改记录：无
'
'
''-----------------------------------------------------------
Public Function CreateSectionStyle(sStyleName As String) As Boolean
    ' Create a new sample line style and add it to the
    ' drawing's collection of such styles.
    Dim oSectionStyle As AeccSectionStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SectionStyles.Remove (sStyleName)
    Set oSectionStyle = g_oDocument.SectionStyles.Item(sStyleName)
    On Error GoTo 0
    If (oSectionStyle Is Nothing) Then
        On Error Resume Next
        Set oSectionStyle = g_oDocument.SectionStyles.Add(sStyleName)
        On Error GoTo 0
        If (oSectionStyle Is Nothing) Then
            Debug.Print "Error creating an sample line style"
            CreateSectionStyle = False
            Exit Function
        End If
    End If

    oSectionStyle.PointDisplayStyle2d.Visible = True
    oSectionStyle.PointDisplayStyle2d.color = 90 ' green
    oSectionStyle.SegmentDisplayStyle2d.Visible = True
    oSectionStyle.SegmentDisplayStyle2d.color = 110 ' green/blue

    CreateSectionStyle = True
End Function ' CreateSectionStyle

Attribute VB_Name = "Section"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


'''---------------------------------------------------------
'
'功能：利用采样线编组中所有采样线创建全部横断面
'
'作者：
'
'
'日期：２００７/０8
'
'
'修改记录：无
'
'
''-----------------------------------------------------------
Public Function CreateSections(oAlignment As AeccAlignment) As Boolean
    '利用采样线编组中所有采样线创建全部横断面
    oAlignment.SampleLineGroups.Item(0).CreateSectionsAtSampleLines
    Dim i As Integer
    Dim j As Integer
    Dim oSampleLineGroup As AeccSampleLineGroup
    Set oSampleLineGroup = oAlignment.SampleLineGroups.Item(0)
    For i = 0 To oSampleLineGroup.SampleLines.Count - 1
        Dim oSections As AeccSections
        Set oSections = oSampleLineGroup.SampleLines.Item(i).Sections
        For j = 0 To oSections.Count - 1
            Debug.Print "横断面 "; oSections.Item(j).Name;
            Debug.Print "的最大高程: "; oSections.Item(j).ElevationMax
            
            oSections.Item(j).DataType = aeccSectionDataTIN
            oSections.Item(j).StaticDynamic = aeccSectionStateDynamic
            ' 不需要设置样式，因为在创建采样线组的时候已经设置
        Next j
    Next i

    CreateSections = True
    


End Function

Attribute VB_Name = "SectionView"
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'



'''---------------------------------------------------------
'
'功能：沿每条路线,在其每条采样线位置创建横断面图。
'
'作者：
'
'
'日期：２００７/０8
'
'
'修改记录：无
'
'
''-----------------------------------------------------------
'
Public Function CreateSectionView(oAlignment As AeccAlignment) As Boolean


    Dim i As Integer
    Dim j As Integer

    ' 创建横断面图样式.
    Dim oSectionViewStyle As AeccSectionViewStyle
    If (CreateSectionViewStyle("Section View style 01") = False) Then
        MsgBox "创建横断面图样式失败"
        CreateSectionView = False
        Exit Function
    End If
    Set oSectionViewStyle = g_oDocument.SectionViewStyles.Item("Section View style 01")


    ' 创建横断面图标注栏集样式
    Dim oSectionViewBandStyleSet As AeccSectionViewBandStyleSet
    If (CreateSectionViewBandStyleSet("Section View band style set 01") = False) Then
        MsgBox "创建横断面图标注栏集样式失败"
        CreateSectionView = False
        Exit Function
    End If
    Set oSectionViewBandStyleSet = g_oDocument.SectionViewBandStyleSets.Item("Section View band style set 01")
    
    
    ' 路线具有采样线组， 遍历路线对象下所有的采样线编组
    For i = 0 To oAlignment.SampleLineGroups.Count - 1
        Dim oSampleLines As AeccSampleLines
        Set oSampleLines = oAlignment.SampleLineGroups.Item(i).SampleLines
        
        ' 现在遍历当前采样线编组中的所有采样线，' 为每条采样线添加一个横断面视图
        ' 放置在单独的位置，使用一种样式，并标注之前定义的数据栏
        Dim dStartX As Double
        Dim dStartY As Double
        Dim dOffsetRight As Double
        Dim dOffsetDown As Double
        dStartX = 6200#
        dStartY = 3600#
        dOffsetRight = 0
        dOffsetDown = 0
        For j = 0 To oSampleLines.Count - 1
            Dim oSectionView As AeccSectionView
            dOffsetRight = j * 300
            dOffsetDown = 900

            If (j > (oSampleLines.Count / 2)) Then
                dOffsetRight = (j - (oSampleLines.Count / 2)) * 300
                dOffsetDown = 400
            End If
            Dim dOriginPt(0 To 2) As Double
            '指定横断面图的位置
            dOriginPt(0) = dStartX + dOffsetRight
            dOriginPt(1) = dStartY + dOffsetDown
            ' 创建横断面图
            Set oSectionView = oSampleLines.Item(j).SectionViews.Add("横断面图 " & CStr(j), "0", dOriginPt, oSectionViewStyle, oSectionViewBandStyleSet)
            ' 创建一个新的横断面图标注栏
            Dim oSectionViewBandSetItem As AeccSectionViewBandSetItem
            Set oSectionViewBandSetItem = oSectionView.BandSet.Add(oSectionViewBandStyleSet.Item(0).BandStyle, oSampleLines.Item(j).Sections.Item(0), oSampleLines.Item(j).Sections.Item(0))
            ' 指定显示位置
            oSectionViewBandSetItem.Location = aeccBandSetItemLocationBottom
            ' 删除第一个横断面图标注栏
            Call oSectionView.BandSet.Remove(0)
            Debug.Print "Gap:"; oSectionView.BandSet.Item(0).Gap
        Next j
    Next i

    CreateSectionView = True
End Function

Attribute VB_Name = "SectionViewStyle"
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'

'''---------------------------------------------------------
'
'功能：创建横断面图样式。
'
'作者：
'
'
'日期：２００７/０8
'
'
'修改记录：无
'
'
''-----------------------------------------------------------
Public Function CreateSectionViewStyle(sStyleName As String) As Boolean
    ' Create a new section view style and add it to the
    ' drawing's collection of such styles.
    Dim oSectionViewStyle As AeccSectionViewStyle
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SectionViewStyles.Remove sStyleName
    Set oSectionViewStyle = g_oDocument.SectionViewStyles.Item(sStyleName)
    On Error GoTo 0
    If (oSectionViewStyle Is Nothing) Then
        On Error Resume Next
        Set oSectionViewStyle = g_oDocument.SectionViewStyles.Add(sStyleName)
        On Error GoTo 0
        If (oSectionViewStyle Is Nothing) Then
            Debug.Print "Error creating a section view style"
            CreateSectionViewStyle = False
            Exit Function
        End If
    End If

    ' Now set the style of the section view.
    
    Dim dOffset(0 To 2) As Double
    With oSectionViewStyle.TopAxis.MajorTickStyle
        .AnnotationDisplayStyle2d.color = 23 ' light brown
        .Height = 0.004 ' text height
        .AnnotationDisplayStyle2d.Visible = True ' show text
        .Interval = 15
        .Text = "<[Section View Point Offset(Um|P1|RN|Sn|AP|OF)]>m"
        .DisplayStyle2d.Visible = True ' show ticks
    End With
    With oSectionViewStyle.TopAxis.TitleStyle
        .DisplayStyle2d.color = 23 ' light brown
        .Height = 0.008 ' text height
        .Text = "Meters"
        dOffset(0) = 0#
        dOffset(1) = 0.02
        .Offset = dOffset
        .DisplayStyle2d.Visible = True
    End With
    
    oSectionViewStyle.BottomAxis.MajorTickStyle.Interval = 15
    oSectionViewStyle.BottomAxis.MajorTickStyle.Text = "<[Section View Point Offset(Uft|P1|RN|Sn|OF|AP)]>ft"
    oSectionViewStyle.BottomAxis.TitleStyle.Text = "Feet"
    dOffset(0) = 0#
    dOffset(1) = -0.02
    oSectionViewStyle.BottomAxis.TitleStyle.Offset = dOffset
    oSectionViewStyle.BottomAxis.TitleStyle.DisplayStyle2d.Visible = True
    
    oSectionViewStyle.GraphStyle.VerticalExaggeration = 4.1
    oSectionViewStyle.GraphStyle.GridStyle.GridsBelowDatum = 1
    oSectionViewStyle.GraphStyle.GridStyle.ClipVertical = False
    oSectionViewStyle.GraphStyle.GridStyle.ClipHorizontal = True
    '
    oSectionViewStyle.GraphStyle.GridStyle.MajorHorizontalDisplayStyle2d.Visible = True
    oSectionViewStyle.GraphStyle.GridStyle.MajorVerticalDisplayStyle2d.Visible = True
    oSectionViewStyle.GraphStyle.GridStyle.MinorHorizontalDisplayStyle2d.Visible = False
    oSectionViewStyle.GraphStyle.GridStyle.MinorVerticalDisplayStyle2d.Visible = False
    '
    dOffset(1) = 0.045
    oSectionViewStyle.GraphStyle.TitleStyle.Offset = dOffset
    oSectionViewStyle.GraphStyle.TitleStyle.Text = "EG at Station <[Section View Station(Uft|FS)]>" 'FS|P2|RN|Sn|OF|AP|B2|TP|EN|W0|DZY)]>"
    
    CreateSectionViewStyle = True
End Function ' CreateSectionViewStyle



'''---------------------------------------------------------
'
'功能：创建横断面图标注栏集样式。
'
'作者：
'
'
'日期：２００７/０8
'
'
'修改记录：无
'
'
''-----------------------------------------------------------
Public Function CreateSectionViewBandStyleSet(sStyleName As String) As Boolean
    ' Create a new band style set and add it to the
    ' drawing's collection of such styles.
    Dim oSectionViewBandStyleSet As AeccSectionViewBandStyleSet
    ' First we try to delete any old styles created
    ' during previous runs of this program.  It might
    ' be that the style is in use, and thus cannot be
    ' removed.  In that case, we will just use the
    ' style that already exists.  If we were able to
    ' delete it, then we will create a new style using
    ' the Add method.
    On Error Resume Next
    g_oDocument.SectionViewBandStyleSets.Remove sStyleName
    Set oSectionViewBandStyleSet = g_oDocument.SectionViewBandStyleSets.Item(sStyleName)
    On Error GoTo 0
    If (oSectionViewBandStyleSet Is Nothing) Then
        On Error Resume Next
        Set oSectionViewBandStyleSet = g_oDocument.SectionViewBandStyleSets.Add(sStyleName)
        On Error GoTo 0
        If (oSectionViewBandStyleSet Is Nothing) Then
            Debug.Print "Error creating a section view style"
            CreateSectionViewBandStyleSet = False
            Exit Function
        End If
    End If

    ' We will modify the style set by adding a band that
    ' has labels both for elevation at each major tick
    ' mark of the graph, and for grade changes at each
    ' grade break.
    '
    ' Remove any old section data band styles that might
    ' exist and create a new style.  It might be that the
    ' style is in use, and cannot be removed.  In that
    ' case, we will use the existing style.
    Dim oBandSectionDataStyle As AeccBandSectionDataStyle
    On Error Resume Next
    g_oDocument.SectionViewBandStyles.SectionDataBandStyles.Remove "Section View data band style 01"
    Set oBandSectionDataStyle = g_oDocument.SectionViewBandStyles.SectionDataBandStyles.Add("Section View data band style 01")
    On Error GoTo 0
    If (oBandSectionDataStyle Is Nothing) Then
        On Error Resume Next
        Set oBandSectionDataStyle = g_oDocument.SectionViewBandStyles.SectionDataBandStyles.Item("Section View data band style 01")
        On Error GoTo 0
        If (oBandSectionDataStyle Is Nothing) Then
            Debug.Print "Error trying to create a section band style."
            CreateSectionViewBandStyleSet = False
            Exit Function
        End If
    End If

    ' Now we can modify how profile views that use this
    ' style will appear.

    ' Display at every major grid line a tick mark and a label
    ' that shows the section elevation at that point.

    ' The major increment label style comes with a text
    ' component, so do not make a new AeccLabelStyleTextComponent
    ' object.  We just modify the existing "Item(0)".
    With oBandSectionDataStyle
        .MajorOffsetLabelDisplayStyle2d.color = 255 ' white
        .MajorOffsetLabelDisplayStyle2d.Visible = True
        .MajorOffsetTickDisplayStyle2d.color = 255 ' white
        .MajorOffsetTickDisplayStyle2d.Visible = True
    End With
    With oBandSectionDataStyle.MajorIncrementLabelStyle.TextComponents.Item(0)
        .Contents = "<[Section1 Elevation(Um|P3|RN|AP|Sn|OF)]>m"
        .color = 255 ' white
        .Visibility = True
        .YOffset = 0.015
    End With
    
    ' Display a red tick mark and a red label showing section
    ' elevation at each vertex endpoint in the sample line.
    ' Make the tick mark large, and only at the top of the
    ' band.
    With oBandSectionDataStyle
        .SampleLineVertexLabelDisplayStyle2d.color = 20 ' red-orange
        .SampleLineVertexLabelDisplayStyle2d.Visible = True
        .SampleLineVertexTickDisplayStyle2d.color = 20 ' red-orange
        .SampleLineVertexTickDisplayStyle2d.Visible = True
    End With
    With oBandSectionDataStyle.SampleLineVerticesLabelStyle.TextComponents.Item(0)
        .Contents = "<[Section1 Elevation(Um|P3|RN|AP|Sn|OF)]>m"
        .color = 20 ' red-orange
        .Visibility = True
        .YOffset = 0.008
    End With
    With oBandSectionDataStyle.SampleLineVerticesLabelStyle.TickStyle
        .IncrementSmallTicksAtMiddle = False
        .IncrementSmallTicksAtBottom = False
        .IncrementSmallTicksAtTop = True
        .SmallTicksAtTopSize = 0.015
    End With
    
    With oBandSectionDataStyle
        oBandSectionDataStyle.CenterLineLabelDisplayStyle2d.color = 220 ' pink (this color has priority)
        oBandSectionDataStyle.CenterLineLabelDisplayStyle2d.Visible = True
        oBandSectionDataStyle.CenterLineLabelStyle.TextComponents.Item(0).color = 255 ' white (this does not have priority - it will be pink)
        oBandSectionDataStyle.CenterLineLabelStyle.TextComponents.Item(0).Visibility = True
    End With

    ' Set the text style of the grade breaks in the data band.
    Dim oLabelStyleTextComponent As AeccLabelStyleTextComponent
    ' If a text component does not exist, we will just skip trying
    ' to set one.
    On Error GoTo EndGradeBand
    Set oLabelStyleTextComponent = oBandSectionDataStyle.GradeBreakLabelStyle.TextComponents.Item(0)
    On Error GoTo 0
    oLabelStyleTextComponent.Contents = "<[Section Segment Grade Change(FP|P2|RN|AP|Sn|OF)]>"
    oLabelStyleTextComponent.Visibility = True
    oLabelStyleTextComponent.color = 252 ' grey
    oLabelStyleTextComponent.BorderStyle.Visibility = True
    oLabelStyleTextComponent.YOffset = -0.015
    oBandSectionDataStyle.GradeBreakLabelDisplayStyle2d.Visible = True
    oBandSectionDataStyle.GradeBreakLabelDisplayStyle2d.color = 252 ' grey
    oBandSectionDataStyle.GradeBreakTickDisplayStyle2d.Visible = True
    oBandSectionDataStyle.GradeBreakTickDisplayStyle2d.color = 252 ' grey
EndGradeBand:
    '
    
    ' Hide all other data displayed in the data band.
    With oBandSectionDataStyle
        .CenterLineLabelDisplayStyle2d.Visible = False
        .CenterLineTickDisplayStyle2d.Visible = False
        .GradeBreakLabelDisplayStyle2d.Visible = False
        .GradeBreakTickDisplayStyle2d.Visible = False
        .MinorOffsetLabelDisplayStyle2d.Visible = False
        .MinorOffsetTickDisplayStyle2d.Visible = False
    End With
    
    ' Set the style of the data band borders and title.
    oBandSectionDataStyle.TitleBoxDisplayStyle2d.color = 10 ' red
    oBandSectionDataStyle.TitleBoxDisplayStyle2d.Linetype = "DOT"
    oBandSectionDataStyle.TitleBoxDisplayStyle2d.Visible = True
    
    oBandSectionDataStyle.TitleBoxTextDisplayStyle2d.color = 80 ' green
    oBandSectionDataStyle.TitleBoxTextDisplayStyle2d.Visible = True
    
    oBandSectionDataStyle.TitleStyle.Text = "Section Elevations" & vbNewLine & vbNewLine & "Grade Breaks"
    oBandSectionDataStyle.TitleStyle.OffsetFromBand = 0.01
    oBandSectionDataStyle.TitleStyle.TextBoxWidth = 0.18
    oBandSectionDataStyle.TitleStyle.TextHeight = 0.0121

    ' Finally, we add the section view data band style
    ' to the profile view style set we created earlier.
    Call oSectionViewBandStyleSet.Add(oBandSectionDataStyle)

    CreateSectionViewBandStyleSet = True
End Function ' CreateSectionViewBandStyleSet

Attribute VB_Name = "Subroutines"
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'
'''---------------------------------------------------------
'
'功能：创建横断面和横断面图
'
'作者：
'
'
'日期：２００７/０8
'
'
'修改记录：无
'
'
''-----------------------------------------------------------
Sub RunSection()

    If ThisDrawing.Name <> "Section_CH08.dwg" Then
        MsgBox "请打开Section_CH08.dwg后重新运行"
        Exit Sub
    
    End If
    
    ' 获取程序和文档对象
    If (GetBaseCivilObjects = False) Then
        MsgBox "获取程序和文档对象失败，退出."
        Exit Sub
    End If
    
    Dim pt As Variant
    Dim oEnt As AcadObject
    
    ThisDrawing.Utility.GetEntity oEnt, pt, "选择路线对象"
    If oEnt.ObjectName <> "AeccDbAlignment" Then
         MsgBox "选择的对象不是路线对象，退出."
        Exit Sub
    End If
    Dim oAlignment As AeccAlignment
    Set oAlignment = oEnt

    If (CreateSampleLineGroup(oAlignment) = False) Then
        MsgBox "创建采样线组失败."
        Exit Sub
    End If
    
    If (CreateSections(oAlignment) = False) Then
        MsgBox "创建横断面失败."
        Exit Sub
    End If

    If (CreateSectionView(oAlignment) = False) Then
        MsgBox "创建横断面图失败."
        Exit Sub
    End If
    
    g_oCivilApp.ZoomExtents
End Sub
