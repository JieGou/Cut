Attribute VB_Name = "Style"
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
''---------------------------------------------------------
'
'功能：创建图形样式
'
'
' 输入参数：sStylename As String
'
'
' 输出参数：AeccSurveyFigureStyle
'
' 作者：
'
' 日期：２００７/０8
'
' 修改记录：无
'
'
''-----------------------------------------------------------

Public Function CreateFigureStyle(sStylename As String) As AeccSurveyFigureStyle
    Dim oFigureStyles As AeccSurveyFigureStyles
    Dim oFigureStyle As AeccSurveyFigureStyle
    
    Set oFigureStyles = g_oSurveyDocument.FigureStyles
    
    On Error Resume Next
    Set oFigureStyle = oFigureStyles.Item(sStylename)
    On Error GoTo 0
    If (oFigureStyle Is Nothing) Then
        On Error Resume Next
        Set oFigureStyle = oFigureStyles.Add(sStylename)
        On Error GoTo 0
        If (oFigureStyle Is Nothing) Then
            Set CreateFigureStyle = Nothing
            Exit Function
        End If
    End If
    
    With oFigureStyle

        .AdditionalMarkersDisplayStyle2d.Visible = True
        .AdditionalMarkersDisplayStyle2d.color = 150 ' blue
        .AdditionalMarkersPlacementMethod = aeccSurveyAdditionalMarkerPlacementMethodAtInterval
        .AdditionalMarkersInterval = 20
        
        '
        .EndpointMarkersDisplayStyle2d.Visible = False
        .IsPlaceMarkerAtFigureEndPoints = False
        .IsPlaceMarkerAtFigureStartPoints = False
        .MidpointMarkersDisplayStyle2d.Visible = False
        .VertexMarkersDisplayStyle2d.Visible = False

        '
        .FigureLinesDisplayStyle2d.Visible = True
        .FigureLinesDisplayStyle2d.color = 90 ' green
    
        .Description = sStylename
        .FigureDisplayMode = aeccSurveyFigureElevationDisplayModeFlattenFigureToElevation
        .FlattenFigureElevation = 1
        .IsAlignAdditionalMarkersWithFigure = True
        .IsAlignMidPointMarkersWithFigure = True
        .IsAlignStartAndEndPointMarkersWithFigure = True
        .IsAlignVertexMarkersWithFigure = True
    End With
    
    Set CreateFigureStyle = oFigureStyle
End Function

Attribute VB_Name = "Survey"
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'

''---------------------------------------------------------
'
'功能：角度-》弧度
'
'
' 输入参数：degrees As Double
'
'
' 输出参数：Double
'
' 作者：
'
' 日期：２００７/０8
'
' 修改记录：无
'
'
''-----------------------------------------------------------
Private Function Rad(degrees As Double) As Double
    If (degrees = 0) Then
        Rad = 0#
        Exit Function
    End If
    
    Rad = (degrees * PI) / 180#
End Function

''---------------------------------------------------------
'
'功能：获取和调整用户设置
'
'
' 输入参数：无
'
'
' 输出参数：Boolean
'
' 作者：
'
' 日期：２００７/０8
'
' 修改记录：无
'
'
''-----------------------------------------------------------
Public Function AdjustUserSettings() As Boolean
    Dim oUserSettings  As AeccSurveyUserSettings
    ' 获取用户设置对象
    Set oUserSettings = g_oSurveyDocument.GetUserSettings
    With oUserSettings
        Dim oColor As New AcadAcCmColor
        .ShowBaseline = True
        oColor.SetRGB 255, 165, 0 ' bright orange
        Set .BaselineColor = oColor
        .ShowForesightPrism = True
        oColor.SetRGB 255, 99, 71 ' tomato
        Set .ForesightPrismColor = oColor
        .EraseAllFigures = False
        .EraseAllObservations = False
        .EraseAllSurveyPoints = False
        ThisDrawing.Utility.Prompt ("缺省层:" + .DefaultFigureLayer + vbCrLf)
    End With
    ' 保存用户设置对象
    g_oSurveyDocument.UpdateUserSettings oUserSettings
    
    AdjustUserSettings = True
End Function



''---------------------------------------------------------
'
'功能：遍历测量设备数据库
'
'
' 输入参数：无
'
'
' 输出参数：无
'
' 作者：
'
' 日期：２００７/０8
'
' 修改记录：无
'
'
''-----------------------------------------------------------
Public Sub EnumerateEquipmentDatabase()
    Dim oEquipDatabases As AeccSurveyEquipmentDatabases
    Dim oEquipDatabase As AeccSurveyEquipmentDatabase
    Dim oEquipment As AeccSurveyEquipment
    
    Set oEquipDatabases = g_oSurveyDocument.EquipmentDatabases
    For Each oEquipDatabase In oEquipDatabases
        ThisDrawing.Utility.Prompt ("测量设备数据库: " + oEquipDatabase.Name + vbCrLf)
        
        For Each oEquipment In oEquipDatabase
        With oEquipment
            ThisDrawing.Utility.Prompt ("//----" + vbCrLf)
            ThisDrawing.Utility.Prompt (" 名称: " + .Name + ",   Id: " + .Id + vbCrLf)
            ThisDrawing.Utility.Prompt (" 描述: " + .Description + vbCrLf)
            ThisDrawing.Utility.Prompt (" 角度单位的类型: " + .AngleType + vbCrLf)
            ThisDrawing.Utility.Prompt (" 角度单位: " + .AngleUnit + vbCrLf)
            ThisDrawing.Utility.Prompt (" 水平瞄准: " + .AzimuthStandard + vbCrLf)
            ThisDrawing.Utility.Prompt (" 波常量: " + .CarrierWaveConstant + vbCrLf)
            ThisDrawing.Utility.Prompt (" 中心误差: " + .CenterStandard + vbCrLf)
            ThisDrawing.Utility.Prompt (" 定点误差: " + .CircleStandard + vbCrLf)
            ThisDrawing.Utility.Prompt (" 坐标误差: " + .CoordinateStandard + vbCrLf)
            ThisDrawing.Utility.Prompt (" 距离单位: " + .DistanceUnit + vbCrLf)
            ThisDrawing.Utility.Prompt (" Edm 常量误差: " + .EdmMmError + "mm" + vbCrLf)
            ThisDrawing.Utility.Prompt (" Edm 比例误差: " + .EdmPpmError + "ppm" + vbCrLf)
            ThisDrawing.Utility.Prompt (" Edm 偏移: " + .EdmOffset + vbCrLf)
            ThisDrawing.Utility.Prompt (" 折射率: " + .FrequencyRefractiveIndex + vbCrLf)
            ThisDrawing.Utility.Prompt (" 垂直瞄准: " + .HorizontalCollimation + vbCrLf)
            ThisDrawing.Utility.Prompt (" 棱镜是否倾斜: " + CStr(.IsTiltedPrism) + vbCrLf)
            ThisDrawing.Utility.Prompt (" 测量设备: " + .MeasuringDevice + vbCrLf)
            ThisDrawing.Utility.Prompt (" 定点误差: " + .PointingStandard + vbCrLf)
            ThisDrawing.Utility.Prompt (" 棱镜常量: " + .PrismConstant + vbCrLf)
            ThisDrawing.Utility.Prompt (" 棱镜偏移: " + .PrismOffset + vbCrLf)
            ThisDrawing.Utility.Prompt (" 棱镜标准: " + .PrismStandard + vbCrLf)
            ThisDrawing.Utility.Prompt (" 修正: " + .Revision + vbCrLf)
            ThisDrawing.Utility.Prompt (" 目标路线误差: " + .TargetStandard + vbCrLf)
            ThisDrawing.Utility.Prompt (" 经纬仪Standard: " + .TheodoliteStandard + vbCrLf)
            ThisDrawing.Utility.Prompt (" 垂直角度类型: " + .VerticalAngleType + vbCrLf)
            ThisDrawing.Utility.Prompt (" 垂直瞄准: " + .VerticalCollimation + vbCrLf)
            ThisDrawing.Utility.Prompt ("----//" + vbCrLf)

        End With
        Next
    Next
End Sub

''---------------------------------------------------------
'
'功能：获取或创建指定的项目
'
'
' 输入参数：无
'
'
' 输出参数：AeccSurveyProject
'
' 作者：
'
' 日期：２００７/０8
'
' 修改记录：无
'
'
''-----------------------------------------------------------
Public Function CreateSurveyProject() As AeccSurveyProject
    Dim oSurveyProject As AeccSurveyProject

    ' 判断项目是否存在，存在则返回
    For Each oSurveyProject In g_oSurveyDocument.Projects
        If (oSurveyProject.Name = "PROJECT_NAME") Then

            Exit For
        End If
    Next
    ' 创建新的项目
    If (oSurveyProject Is Nothing) Then
        Set oSurveyProject = g_oSurveyDocument.Projects.Create("PROJECT_NAME")
        If (oSurveyProject Is Nothing) Then
            ThisDrawing.Utility.Prompt ("创建新的项目失败" + vbCrLf)
            Set CreateSurveyProject = Nothing
            Exit Function
        End If
    End If
    
    Set CreateSurveyProject = oSurveyProject
End Function

''---------------------------------------------------------
'
'功能：更新指定的项目设置
'
'
' 输入参数：oSurveyProject As AeccSurveyProject
'
'
' 输出参数：Boolean
'
' 作者：
'
' 日期：２００７/０8
'
' 修改记录：无
'
'
''-----------------------------------------------------------
Public Function AdjustProjectSettings(oSurveyProject As AeccSurveyProject) As Boolean
    Dim oProjectSettings As AeccSurveyProjectSettings
    Set oProjectSettings = oSurveyProject.GetProjectSettings()
    
    '设置当前项目设置
    With oProjectSettings
        .AngleType = aeccSurveyAngleTypeAzimuth
    End With
    
    ' 更新当前项目设置
    oSurveyProject.UpdateProjectSettings oProjectSettings
    
    AdjustProjectSettings = True
End Function



''---------------------------------------------------------
'
'功能：创建测量网络
'
'
' 输入参数：oSurveyProject As AeccSurveyProject
'
'
' 输出参数：Boolean
'
' 作者：
'
' 日期：２００７/０8
'
' 修改记录：无
'
'
''-----------------------------------------------------------
Public Function CreateSurveyNetwork(oSurveyProject As AeccSurveyProject) As Boolean
    Dim oSurveyDatabase As AeccSurveyDatabase
    Dim oSurveyNetwork As AeccSurveyNetwork
    Dim dAngle As Double
    
    '删除已经存在的测量网络
    For Each oSurveyNetwork In oSurveyProject.Networks
        If (oSurveyNetwork.Name = "NETWORK_NAME") Then
            oSurveyProject.Networks.Remove oSurveyNetwork
            Exit For
        End If
    Next
    
    '创建测量网络
    Set oSurveyNetwork = oSurveyProject.Networks.Create("NETWORK_NAME")
    If (oSurveyNetwork Is Nothing) Then
        ThisDrawing.Utility.Prompt ("创建测量网络" + vbCrLf)
        CreateSurveyNetwork = False
        Exit Function
    End If
    
    ' 获取控制点对象集合
    Dim oControlPoints As AeccSurveyControlPoints
    Set oControlPoints = oSurveyNetwork.ControlPoints
    ' 创建控制点， 编号: 3001,位置（5000.0m, 5000.0m）, 高程 100.0m
    Dim oControlPoint As AeccSurveyControlPoint
    Set oControlPoint = oControlPoints.Create(3001, "通过API创建的控制点", "", 5000#, 5000#, 100#)


    '  获取方向集合
    Dim oDirections As AeccSurveyDirections
    Set oDirections = oSurveyNetwork.Directions
    ' 从点3001到点3004以45.0方位角创建方向
    Dim oNewDirection As AeccSurveyDirection
    Set oNewDirection = oDirections.Create(3001, 3004, Rad(45#), aeccSurveyDirectionTypeAzimuth)
    
    Dim oSetups As AeccSurveySetups
    Dim oSetup1 As AeccSurveySetup
    Dim oSetup2 As AeccSurveySetup
    Dim oSetup3 As AeccSurveySetup
    Dim oSetup4 As AeccSurveySetup
    
    Dim oObservations As AeccSurveyObservations
    Dim oObservation1 As AeccSurveyObservation
    Dim oObservation2 As AeccSurveyObservation
    Dim oObservation3 As AeccSurveyObservation
    Dim oObservation4 As AeccSurveyObservation
    
    Set oSetups = oSurveyNetwork.Setups

    
    ' 创建一个设置：编号3001带后视3004 (后视方向自动计算)
    Set oSetup1 = oSetups.Create(3001, 3004)
    ThisDrawing.Utility.Prompt ("方向:" + CStr(oSetup1.BacksightDirection) + vbCrLf)
    ThisDrawing.Utility.Prompt ("方位:" + CStr(oSetup1.BacksightOrientation) + vbCrLf)
    
    ' 设置 "位置:3001, 后视:3004" 创建对点3002的观测
    '    Angle = 1.5708 radians (90.0 degrees)
    '    Angle Type = Angle
    '    Distance = 100.0 meters
    '    Distance Type = Slope
    '    Vertical = 1.5708 radians (90.0 degrees)
    '    Vertical Type = Vertical Angle
    '    Target Height = 0.0 meters
    '    Target Type = Prism
    Set oObservations = Nothing
    Set oObservations = oSetup1.Observations
    Set oObservation1 = oObservations.Create(3002, aeccSurveyAngleTypeAngle, Rad(90#), aeccSurveyDistanceTypeSlope, 100#, aeccSurveyVerticalTypeVerticalAngle, Rad(90#), aeccSurveyTargetTypePrism, 0#, "观测1: 从设置<位置:3001, 后视:3004> 到点 3002")
    ' 从测量设备数据，点3002的位置可以确定
    ThisDrawing.Utility.Prompt ("点 3002位于:东距" + CStr(oObservation1.Easting))
    ThisDrawing.Utility.Prompt (",北距 " + CStr(oObservation1.Northing) + vbCrLf)
    
    ' 创建一个设置：编号3001带后视3001 (后视方向自动计算)
    Set oSetup2 = oSetups.Create(3002, 3001)
    ' 创建到点3003的观测,设置 "位置:2, 后视:1"
    Set oObservations = Nothing
    Set oObservations = oSetup2.Observations
    Set oObservation2 = oObservations.Create(3003, aeccSurveyAngleTypeAngle, Rad(90#), aeccSurveyDistanceTypeSlope, 100#, aeccSurveyVerticalTypeVerticalAngle, Rad(90#), aeccSurveyTargetTypePrism, 0#, "观测2: 从设置<位置:3002, 后视:3001> 到点 3003")
    
    ' 创建设置编号3003 带后视3002
    Set oSetup3 = oSetups.Create(3003, 3002)
    ' 创建到点3004的观测,设置 "位置:3, 后视:2"
    Set oObservations = Nothing
    Set oObservations = oSetup3.Observations
    Set oObservation3 = oObservations.Create(3004, aeccSurveyAngleTypeAngle, Rad(90#), aeccSurveyDistanceTypeSlope, 100#, aeccSurveyVerticalTypeVerticalAngle, Rad(90#), aeccSurveyTargetTypePrism, 0#, "观测3: 从设置<位置:3003, 后视:3003> 到点 3004")
    
    ' 创建设置编号 3004 带后视 3003
    Set oSetup4 = oSetups.Create(3004, 3003)
     ' 创建到点 3001 的观测,设置 "位置:4, 后视:3"
    Set oObservations = Nothing
    Set oObservations = oSetup4.Observations
    Set oObservation4 = oObservations.Create(3001, aeccSurveyAngleTypeAngle, Rad(90), aeccSurveyDistanceTypeSlope, 100#, aeccSurveyVerticalTypeVerticalAngle, Rad(90), aeccSurveyTargetTypePrism, 0#, "观测4: 从设置<位置:3004, 后视:3003> 到点 3001")
    
    
    '创建非控制点，编号：3006，位置4950.0, 5000.0, 高程 120.0
    Dim oNonControlPoint As AeccSurveyNonControlPoint
    Set oNonControlPoint = oSurveyNetwork.NonControlPoints.Create(3006, "NONCONTROL_POINT_NAME", "非控制点描述", 4950#, 5000#, 100#)


   
    ' 创建导线测量，控制点3001，通过点3002，3002，3004，最后回到开始控制点
    Dim oTraverse As AeccSurveyTraverse
    Dim lStations(0 To 2) As Long
    lStations(0) = 3002
    lStations(1) = 3003
    lStations(2) = 3004
    Set oTraverse = oSurveyNetwork.Traverses.Create("TRAVERSE_NAME", 3001, 3004, 3001, lStations)
    
    
    '使修改在图形中可见
    oSurveyNetwork.AddToDrawing
    oSurveyNetwork.UpdateNetwork
    
    ' 缩放视图
    g_oSurveyApplication.ZoomExtents
    
    '
    CreateSurveyNetwork = True
End Function
''---------------------------------------------------------
'
'功能：创建测量图形
'
'
' 输入参数：oSurveyProject As AeccSurveyProject
'
'
' 输出参数：Boolean
'
' 作者：
'
' 日期：２００７/０8
'
' 修改记录：无
'
'
''-----------------------------------------------------------
Public Function CreateSurveyFigure(oSurveyProject As AeccSurveyProject) As Boolean
    Dim oFigure As AeccSurveyFigure
    
    '删除已经存在的测量图形
    If (oSurveyProject.Figures.Count > 0) Then
        For Each oFigure In oSurveyProject.Figures
            If (oFigure.Name = "FIGURE_NAME") Then
                On Error Resume Next
                oSurveyProject.Figures.Remove oFigure.Id
                On Error GoTo 0
                Exit For
            End If
        Next
    End If
    
    ' 创建测量图形
    Set oFigure = oSurveyProject.Figures.Create("FIGURE_NAME")
    If (oFigure Is Nothing) Then
        Debug.Print "创建测量图形失败，退出"
        CreateSurveyFigure = False
        Exit Function
    End If
    
    ' 获取创建测量图形的点
    Dim oPoint1 As AeccSurveyPoint
    Dim oPoint2 As AeccSurveyPoint
    Dim oPoint3 As AeccSurveyPoint
    Dim oPoint4 As AeccSurveyPoint
    Set oPoint1 = oSurveyProject.GetPointByNumber(3001)
    Set oPoint2 = oSurveyProject.GetPointByNumber(3002)
    Set oPoint3 = oSurveyProject.GetPointByNumber(3003)
    Set oPoint4 = oSurveyProject.GetPointByNumber(3004)

    ' 根据指定点的位置向图形对象中添加直线
    oFigure.AddLineByPoint oPoint1.Easting - 100, oPoint1.Northing - 100, 3001
    oFigure.AddLineByPoint oPoint2.Easting - 100, oPoint2.Northing - 100, 3002
    oFigure.AddLineByPoint oPoint3.Easting - 100, oPoint3.Northing - 100, 3003
    oFigure.AddLineByPoint oPoint4.Easting - 100, oPoint4.Northing - 100, 3004
    oFigure.AddLineByPoint oPoint1.Easting - 100, oPoint1.Northing - 100, 3001
    oFigure.IsBreakline = False
    oFigure.IsLotLine = False
    oFigure.Layer = "0"
    ' 设置样式
    oFigure.Style = CreateFigureStyle("FIGURE_STYLE_NAME").Name
    
    '绘制一条30米长与主轴成12夹角的线
    oFigure.AddLineByAzimuthDistance 0.17453, 30
    ' 20米长在从前一条线 成270 °夹角位置
    oFigure.AddLineByDeltaAzimuthDistance 4.7124, 20

    ' 创建顺时针的半圆弧, 终点在测量点3001.
    oFigure.AddArc 10, 0.5, 4888, 4921, oPoint1.Easting - 100, oPoint1.Northing - 100, , 3001
  
    oFigure.Save
    oFigure.AddToDrawing

    ' 缩放视图
    g_oSurveyApplication.ZoomExtents
    
    CreateSurveyFigure = True
End Function

Attribute VB_Name = "SurveyObject"
'
' Copyright {2003-2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'

Option Explicit
' 声明全局的程序、文档对象
'
Public g_oSurveyApplication As AeccSurveyApplication
Public g_oSurveyDocument As AeccSurveyDocument




''---------------------------------------------------------
'
'功能：获取测量模块的程序、文档对象
'
'
' 输入参数：无
'
'
' 输出参数：Boolean
'
' 作者：
'
' 日期：２００７/０8
'
' 修改记录：无
'
'
''-----------------------------------------------------------
Function GetSurveyObject() As Boolean
    Dim oApp As AcadApplication
    Set oApp = ThisDrawing.Application
    Dim sAppName As String
    ' 注意：需要指定版本号（5.0）
    sAppName = "AeccXUiSurvey.AeccSurveyApplication.5.0"
    On Error Resume Next
    Set g_oSurveyApplication = oApp.GetInterfaceObject(sAppName)
    On Error GoTo 0
    If (g_oSurveyApplication Is Nothing) Then
        MsgBox "创建程序失败 " & sAppName & ", 退出."
        GetSurveyObject = False
        Exit Function
    End If
    Set g_oSurveyDocument = g_oSurveyApplication.ActiveDocument
    GetSurveyObject = True
End Function

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
Option Explicit


Public Sub SurverSample()

    ' 获取测量程序对象
    
    If GetSurveyObject = False Then
        MsgBox "获取测量程序对象失败，退出"
        Exit Sub
    End If
    
    Dim oSurveyProject As AeccSurveyProject
    Set oSurveyProject = CreateSurveyProject()
        
     If (oSurveyProject Is Nothing) Then
        MsgBox "创建工程失败，退出"
        Exit Sub
    End If

    '创建测量网络
    If (CreateSurveyNetwork(oSurveyProject) = False) Then
        MsgBox "创建测量网络，退出"
        Exit Sub
    End If
    
    
    ' 创建测量图形.
    If (CreateSurveyFigure(oSurveyProject) = False) Then
        MsgBox "创建测量图形，退出"
        Exit Sub
    End If


End Sub
