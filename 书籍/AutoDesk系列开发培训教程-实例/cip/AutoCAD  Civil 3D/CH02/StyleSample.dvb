Attribute VB_Name = "BaseObjects"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' 声明全局的程序、文档和数据库对象
Public g_oCivilApp As AeccApplication
Public g_oDocument As AeccDocument
Public g_oAeccDb As AeccDatabase


''---------------------------------------------------------
'
'功能：获取模块的程序、文档和数据库对象
'
'作者：
'
'
'日期：２００７/０8
'
'
'修改记录：无
'
'
''-----------------------------------------------------------
Public Function GetBaseCivilObjects() As Boolean
    Dim oApp As AcadApplication
    Set oApp = ThisDrawing.Application
    '需要指定版本号（5.0）.
    Const sAppName = "AeccXUiLand.AeccApplication.5.0"
    Set g_oCivilApp = oApp.GetInterfaceObject(sAppName)
    If g_oCivilApp Is Nothing Then
        MsgBox "获取程序对象 " & sAppName & "错误, 退出."
        GetBaseCivilObjects = False
        Exit Function
    End If
    Set g_oDocument = g_oCivilApp.ActiveDocument
    Set g_oAeccDb = g_oDocument.Database
    GetBaseCivilObjects = True
End Function

Attribute VB_Name = "PointStyle"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


''---------------------------------------------------------
'
'功能：创建点样式
'
'作者：
'
'
'日期：２００７/０8
'
'
'修改记录：无
'
'
''-----------------------------------------------------------
'
Public Function CreatePointStyle(sStyleName As String) As Boolean
    Dim oPointStyle As AeccPointStyle
    Dim oPointStyles As AeccPointStyles
    Set oPointStyles = g_oDocument.PointStyles
    
    '
    On Error Resume Next
    Set oPointStyle = oPointStyles.Item(sStyleName)
    ' 创建点样式对象.
    On Error GoTo 0
    If (oPointStyle Is Nothing) Then
        Set oPointStyle = oPointStyles.Add(sStyleName)
    End If

    '  设置所创建点样式对象的属性
    oPointStyle.MarkerType = aeccUseCustomMarker
    oPointStyle.CustomMarkerStyle = aeccCustomMarkerDot
    oPointStyle.CustomMarkerSuperimposeStyle = aeccCustomMarkerSuperimposeCircle

    CreatePointStyle = True
End Function


''---------------------------------------------------------
'
'功能：创建标签样式
'
'作者：
'
'
'日期：２００７/０8
'
'
'修改记录：无
'
'
''-----------------------------------------------------------
Public Function CreateLabelStyle(oLabelStyle As AeccLabelStyle) As Boolean
    Dim oLabelStyleTickComponent As AeccLabelStyleTickComponent
    Dim oLabelStyleBlockComponent As AeccLabelStyleBlockComponent
    Dim oLabelStyleLineComponent As AeccLabelStyleLineComponent
    Dim oLabelStyleTextComponent As AeccLabelStyleTextComponent

    '
    On Error Resume Next
    '以添加记号组件
    oLabelStyle.TickComponents.Remove "New Tick"
    Set oLabelStyleTickComponent = oLabelStyle.TickComponents.Item("New Tick")
    On Error GoTo 0
    If (oLabelStyleTickComponent Is Nothing) Then
        Set oLabelStyleTickComponent = oLabelStyle.TickComponents.Add("New Tick")
    End If

    oLabelStyleTickComponent.Lineweight.Value = 60 ' .60 mm
    oLabelStyleTickComponent.AlignWithObject = True ' perpendicular to alignment
    oLabelStyleTickComponent.Angle = 0# ' in radians
    oLabelStyleTickComponent.Visibility = True

    ' 向标签样式添加块组件
    On Error Resume Next
    oLabelStyle.BlockComponents.Remove "New Block"
    Set oLabelStyleBlockComponent = oLabelStyle.BlockComponents.Item("New Block")
    On Error GoTo 0
    If (oLabelStyleBlockComponent Is Nothing) Then
        Set oLabelStyleBlockComponent = oLabelStyle.BlockComponents.Add("New Block")
    End If
    'oLabelStyleBlockComponent.BlockName = "AeccTickCircle"
    oLabelStyleBlockComponent.Visibility = True
    
    ' 向标签样式添加直线组件
    On Error Resume Next
    oLabelStyle.LineComponents.Remove "New Line"
    Set oLabelStyleLineComponent = oLabelStyle.LineComponents.Item("New Line")
    On Error GoTo 0
    If (oLabelStyleLineComponent Is Nothing) Then
        Set oLabelStyleLineComponent = oLabelStyle.LineComponents.Add("New Line")
    End If
    oLabelStyleLineComponent.color = 40 ' orange-yellow
    oLabelStyleLineComponent.Angle = 0.7854 ' 2.094 ' radians, = 120 degrees
    oLabelStyleLineComponent.Length = 0.015
    oLabelStyleLineComponent.StartPointXOffset = 0.005
    oLabelStyleLineComponent.StartPointYOffset = 0.005
    oLabelStyleLineComponent.Visibility = True

    '向标签添加文本组件
    Set oLabelStyleTextComponent = oLabelStyle.TextComponents.Item(0)

    'oLabelStyleTextComponent.AllowToCurve = True
    oLabelStyleTextComponent.XOffset = -0.01
    oLabelStyleTextComponent.YOffset = 0.008
    oLabelStyleTextComponent.Contents = "N<[Point Number]>"
    oLabelStyleTextComponent.color = 253
    CreateLabelStyle = True
End Function



''---------------------------------------------------------
'
'功能：创建面样式
'
'作者：
'
'
'日期：２００７/０8
'
'
'修改记录：无
'
'
''-----------------------------------------------------------
Public Function CreateSurfaceStyle(sStyleName As String) As Boolean
    Dim oSurfaceStyle As AeccSurfaceStyle
    Dim oSurfaceStyles As AeccSurfaceStyles
    Set oSurfaceStyles = g_oDocument.SurfaceStyles
    
    ' 创面面样式
    On Error Resume Next
    Set oSurfaceStyle = oSurfaceStyles.Item(sStyleName)
    On Error GoTo 0
    If (oSurfaceStyle Is Nothing) Then
        Set oSurfaceStyle = oSurfaceStyles.Add(sStyleName)
    End If

    ' 设置面样式
    oSurfaceStyle.ContourStyle.SmoothContours = True
    oSurfaceStyle.ContourStyle.SmoothingFactor = 10
    oSurfaceStyle.ContourStyle.SmoothingType = aeccAddVerticies
    oSurfaceStyle.ContourStyle.MinorContourDisplayStyle2d.Visible = True
    oSurfaceStyle.ContourStyle.MajorContourDisplayStyle3d.Visible = True
    oSurfaceStyle.ContourStyle.MinorContourDisplayStyle2d.Visible = True
    oSurfaceStyle.ContourStyle.MinorContourDisplayStyle3d.Visible = True
    oSurfaceStyle.ContourStyle.MinorContourInterval = 0.5
    oSurfaceStyle.ContourStyle.MajorContourColorScheme = "Greens"
    oSurfaceStyle.ContourStyle.MinorContourColorScheme = "Land"
    oSurfaceStyle.ContourStyle.UseColorScheme = True
    oSurfaceStyle.ContourStyle.MajorContourDisplayStyle2d.color = 43
    oSurfaceStyle.ContourStyle.MajorContourDisplayStyle3d.color = 43
    oSurfaceStyle.ContourStyle.MinorContourDisplayStyle2d.color = 47
    oSurfaceStyle.ContourStyle.MinorContourDisplayStyle3d.color = 47
    oSurfaceStyle.TriangleStyle.DisplayStyle2d.Visible = False
    oSurfaceStyle.TriangleStyle.DisplayStyle3d.Visible = False
    oSurfaceStyle.BoundaryStyle.DisplayStyle2d.Visible = True
    oSurfaceStyle.BoundaryStyle.DisplayStyle3d.Visible = True
    oSurfaceStyle.BoundaryStyle.DisplayStyle2d.color = 40
    oSurfaceStyle.BoundaryStyle.DisplayStyle3d.color = 40
    oSurfaceStyle.PointStyle.DisplayStyle2d.Visible = True
    oSurfaceStyle.PointStyle.DisplayStyle3d.Visible = True
    oSurfaceStyle.PointStyle.DisplayStyle2d.color = 20
    oSurfaceStyle.PointStyle.DisplayStyle3d.color = 20
    oSurfaceStyle.PointStyle.DataPointsDisplayType = 0
    
    CreateSurfaceStyle = True
End Function

Attribute VB_Name = "Subroutines"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit




''---------------------------------------------------------
'
'功能：创建样式
'
'作者：
'
'
'日期：２００７/０8
'
'
'修改记录：无
'
'
''-----------------------------------------------------------
Sub CreateStyle()
    ' 获取程序对象
    If (GetBaseCivilObjects() = False) Then
        MsgBox "获取程序对象失败"
        Exit Sub
    End If
    
    If (CreatePointStyle("Point_Style_01") = False) Then
        Debug.Print "创建点样式失败"
        Exit Sub
    End If
    
    If (CreateSurfaceStyle("Surface_Style_01") = False) Then
        Debug.Print "创建面样式失败."
        Exit Sub
    End If
    
    Dim oLabelStyle As AeccLabelStyle

    ' 创建新的标签样式
    On Error Resume Next
    g_oDocument.PointLabelStyles.Remove "POINT_LABEL_STYLE_01"
    Set oLabelStyle = g_oDocument.PointLabelStyles.Add("POINT_LABEL_STYLE_01")
    On Error GoTo 0
    If (oLabelStyle Is Nothing) Then
        On Error Resume Next
        Set oLabelStyle = g_oDocument.PointLabelStyles.Item("POINT_LABEL_STYLE_01")
        On Error GoTo 0
        If (oLabelStyle Is Nothing) Then
            Exit Sub
        End If
    End If
    
    ' 设置标签样式
    Call CreateLabelStyle(oLabelStyle)

End Sub
