Attribute VB_Name = "BaseObjects"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' 声明全局的程序、文档和数据库对象
Public g_oCivilApp As AeccApplication
Public g_oDocument As AeccDocument
Public g_oAeccDb As AeccDatabase


''---------------------------------------------------------
'
'功能：获取模块的程序、文档和数据库对象
'
'作者：
'
'
'日期：２００７/０8
'
'
'修改记录：无
'
'
''-----------------------------------------------------------
Public Function GetBaseCivilObjects() As Boolean
    Dim oApp As AcadApplication
    Set oApp = ThisDrawing.Application
    '需要指定版本号（5.0）.
    Const sAppName = "AeccXUiLand.AeccApplication.5.0"
    Set g_oCivilApp = oApp.GetInterfaceObject(sAppName)
    If g_oCivilApp Is Nothing Then
        MsgBox "获取程序对象 " & sAppName & "错误, 退出."
        GetBaseCivilObjects = False
        Exit Function
    End If
    Set g_oDocument = g_oCivilApp.ActiveDocument
    Set g_oAeccDb = g_oDocument.Database
    GetBaseCivilObjects = True
End Function

Attribute VB_Name = "PointStyle"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


''---------------------------------------------------------
'
'功能：创建点样式
'
'作者：
'
'
'日期：２００７/０8
'
'
'修改记录：无
'
'
''-----------------------------------------------------------
'
Public Function CreatePointStyle(sStyleName As String) As Boolean
    Dim oPointStyle As AeccPointStyle
    Dim oPointStyles As AeccPointStyles
    Set oPointStyles = g_oDocument.PointStyles
    
    '
    On Error Resume Next
    Set oPointStyle = oPointStyles.Item(sStyleName)
    ' 创建点样式对象.
    On Error GoTo 0
    If (oPointStyle Is Nothing) Then
        Set oPointStyle = oPointStyles.Add(sStyleName)
    End If

    '  设置所创建点样式对象的属性
    oPointStyle.MarkerType = aeccUseCustomMarker
    oPointStyle.CustomMarkerStyle = aeccCustomMarkerDot
    oPointStyle.CustomMarkerSuperimposeStyle = aeccCustomMarkerSuperimposeCircle

    CreatePointStyle = True
End Function


''---------------------------------------------------------
'
'功能：创建标签样式
'
'作者：
'
'
'日期：２００７/０8
'
'
'修改记录：无
'
'
''-----------------------------------------------------------
Public Function CreateLabelStyle(oLabelStyle As AeccLabelStyle) As Boolean
    Dim oLabelStyleTickComponent As AeccLabelStyleTickComponent
    Dim oLabelStyleBlockComponent As AeccLabelStyleBlockComponent
    Dim oLabelStyleLineComponent As AeccLabelStyleLineComponent
    Dim oLabelStyleTextComponent As AeccLabelStyleTextComponent

    '
    On Error Resume Next
    '以添加记号组件
    oLabelStyle.TickComponents.Remove "New Tick"
    Set oLabelStyleTickComponent = oLabelStyle.TickComponents.Item("New Tick")
    On Error GoTo 0
    If (oLabelStyleTickComponent Is Nothing) Then
        Set oLabelStyleTickComponent = oLabelStyle.TickComponents.Add("New Tick")
    End If

    oLabelStyleTickComponent.Lineweight.Value = 60 ' .60 mm
    oLabelStyleTickComponent.AlignWithObject = True ' perpendicular to alignment
    oLabelStyleTickComponent.Angle = 0# ' in radians
    oLabelStyleTickComponent.Visibility = True

    ' 向标签样式添加块组件
    On Error Resume Next
    oLabelStyle.BlockComponents.Remove "New Block"
    Set oLabelStyleBlockComponent = oLabelStyle.BlockComponents.Item("New Block")
    On Error GoTo 0
    If (oLabelStyleBlockComponent Is Nothing) Then
        Set oLabelStyleBlockComponent = oLabelStyle.BlockComponents.Add("New Block")
    End If
    'oLabelStyleBlockComponent.BlockName = "AeccTickCircle"
    oLabelStyleBlockComponent.Visibility = True
    
    ' 向标签样式添加直线组件
    On Error Resume Next
    oLabelStyle.LineComponents.Remove "New Line"
    Set oLabelStyleLineComponent = oLabelStyle.LineComponents.Item("New Line")
    On Error GoTo 0
    If (oLabelStyleLineComponent Is Nothing) Then
        Set oLabelStyleLineComponent = oLabelStyle.LineComponents.Add("New Line")
    End If
    oLabelStyleLineComponent.color = 40 ' orange-yellow
    oLabelStyleLineComponent.Angle = 0.7854 ' 2.094 ' radians, = 120 degrees
    oLabelStyleLineComponent.Length = 0.015
    oLabelStyleLineComponent.StartPointXOffset = 0.005
    oLabelStyleLineComponent.StartPointYOffset = 0.005
    oLabelStyleLineComponent.Visibility = True

    '向标签添加文本组件
    Set oLabelStyleTextComponent = oLabelStyle.TextComponents.Item(0)

    oLabelStyleTextComponent.AllowToCurve = True
    oLabelStyleTextComponent.XOffset = -0.01
    oLabelStyleTextComponent.YOffset = 0.008
    oLabelStyleTextComponent.Contents = "N<[Point Number]>"
    oLabelStyleTextComponent.color = 253
    CreateLabelStyle = True
End Function

Attribute VB_Name = "Points"
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


Private g_oPointGroup As AeccPointGroup

''---------------------------------------------------------
'
'功能：点集合中一次添加多个点
'
'作者：
'
'
'日期：２００７/０8
'
'
'修改记录：无
'
'
''-----------------------------------------------------------
Public Function EnumExistingPoints() As Boolean
    Dim oPoints As AeccPoints
    Set oPoints = g_oDocument.Points
    
    ' 添加一组点的坐标到文档的点集合中
    Dim lCountAdded As Long
    Dim vLocations As Variant
    Const NUM_LOCATIONS As Long = 3
    Dim dLocations(0 To (3 * NUM_LOCATIONS) - 1) As Double ' 3 for each point location
    dLocations(0) = 4927: dLocations(1) = 3887: dLocations(2) = 150
    dLocations(3) = 5101: dLocations(4) = 3660: dLocations(5) = 250
    dLocations(6) = 5144: dLocations(7) = 3743: dLocations(8) = 350
    ' AddMultiple 方法接受点数组Variant类型参数
    vLocations = dLocations
    lCountAdded = oPoints.AddMultiple(NUM_LOCATIONS, dLocations, 0)
    
    Dim i As Long
    Dim avgEasting As Double
    Dim avgNorthing As Double
    Dim avgElevation As Double

    Dim oPoint As AeccPoint
    For Each oPoint In oPoints
        avgEasting = avgEasting + oPoint.Easting
        avgNorthing = avgNorthing + oPoint.Northing
        avgElevation = avgElevation + oPoint.Elevation
    Next
    avgEasting = avgEasting / oPoints.Count
    avgNorthing = avgNorthing / oPoints.Count
    avgElevation = avgElevation / oPoints.Count
    MsgBox "平均高程: " & avgElevation & vbNewLine & "点数目: " & oPoints.Count
    EnumExistingPoints = True
End Function ' enumExistingPoints




''---------------------------------------------------------
'
'功能：点集合中添加新点
'
'作者：
'
'
'日期：２００７/０8
'
'
'修改记录：无
'
'
''-----------------------------------------------------------
Public Function CreatePoints() As Boolean
   '
    Dim i As Integer
    Dim dLocation1(0 To 2) As Double
    Dim dLocation2(0 To 2) As Double
    Dim dLocation3(0 To 2) As Double
    dLocation1(0) = 495.8: dLocation1(1) = 407.8: dLocation1(2) = 40#
    dLocation2(0) = 550.7: dLocation2(1) = 317.6: dLocation2(2) = 30#
    dLocation3(0) = 417.7: dLocation3(1) = 353.9: dLocation3(2) = 20#
    '获取文档的点集合
    Dim oPoints As AeccPoints
    Set oPoints = g_oDocument.Points
    
    Dim oPoint1 As AeccPoint
    Dim oPoint2 As AeccPoint
    Dim oPoint3 As AeccPoint
    
    ' 所有点必须包含唯一的名称
    Dim bFound As Boolean
    Dim lFoundAt As Long
    bFound = False
    ' 遍历所有的点，检查点的名称
    For i = 0 To oPoints.Count - 1
        If (oPoints.Item(i).Name = "point1") Then
            bFound = True
            ' 点只能通过索引访问
            lFoundAt = i
        End If
    Next i
    ' 创建点1
    If (bFound = True) Then
        Set oPoint1 = oPoints.Item(lFoundAt)
    Else
        Set oPoint1 = oPoints.Add(dLocation1)
        oPoint1.Name = "point1"
    End If

    ' 创建点2
    Set oPoint2 = oPoints.Add(dLocation2)
    oPoint2.Name = "point2"
    
    ' 创建点3
    Set oPoint3 = oPoints.Add(dLocation3)
    oPoint3.Name = "point3"
    
    '''''''''''''''''''''''''''''''''''''''''''''''''''''''''''
    ' 设置点的样式
    
    ' 调整point1的样式
    
    If (CreatePointStyle("POINT_STYLE_01") = False) Then
        CreatePoints = False
        Exit Function
    End If
    oPoint1.Style = g_oDocument.PointStyles.Item("POINT_STYLE_01")
    oPoint1.RawDescription = "Using: " & "POINT_STYLE_01"
    
    ' 调整point2的样式

    oPoint2.Style = g_oDocument.PointStyles.Item(1) ' Use whatever the second style is.
    oPoint2.RawDescription = "Using: " & g_oDocument.PointStyles.Item(1).Name


    '''''''''''''''''''''''''''''''''''''''''''''''''''''''''''
    '设置点标签样式
        

    Dim oLabelStyle As AeccLabelStyle

    ' 创建新的点标签样式
    On Error Resume Next
    g_oDocument.PointLabelStyles.Remove "POINT_LABEL_STYLE_01"
    Set oLabelStyle = g_oDocument.PointLabelStyles.Add("POINT_LABEL_STYLE_01")
    On Error GoTo 0
    If (oLabelStyle Is Nothing) Then
        On Error Resume Next
        Set oLabelStyle = g_oDocument.PointLabelStyles.Item("POINT_LABEL_STYLE_01")
        On Error GoTo 0
        If (oLabelStyle Is Nothing) Then
            CreatePoints = False
            Exit Function
        End If
    End If
    
    ' 设置point1的标签样式
    Call CreateLabelStyle(oLabelStyle)
    oPoint1.LabelStyle = oLabelStyle
    
    g_oCivilApp.Update
    
    CreatePoints = True
End Function


''---------------------------------------------------------
'
'功能：创建一个点的描述码
'
'作者：
'
'
'日期：２００７/０8
'
'
'修改记录：无
'
'
''-----------------------------------------------------------
Public Function CreatePointDescriptionKey() As Boolean
    ' 创建点样式
    Dim oPointStyle As AeccPointStyle
    On Error Resume Next
    Set oPointStyle = g_oDocument.PointStyles.Item("POINT_STYLE_01")
    On Error GoTo 0
    If (oPointStyle Is Nothing) Then
        If (CreatePointStyle("POINT_STYLE_01") = False) Then
            CreatePointDescriptionKey = False
            Exit Function
        End If
        Set oPointStyle = g_oDocument.PointStyles.Item("POINT_STYLE_01")
    End If
    
    Dim oLabelStyle As AeccLabelStyle
    On Error Resume Next
    Set oLabelStyle = g_oDocument.PointLabelStyles.Item("POINT_LABEL_STYLE_01")
    On Error GoTo 0
    If (oLabelStyle Is Nothing) Then
    ' 创建点标签样式
        On Error Resume Next
        Set oLabelStyle = g_oDocument.PointLabelStyles.Add("POINT_LABEL_STYLE_01")
        On Error GoTo 0
        If (oLabelStyle Is Nothing) Then
            CreatePointDescriptionKey = False
            Exit Function
        End If
        Call CreateLabelStyle(oLabelStyle)
    End If
    
    '创建一个描述码集合
    Dim oPointDescriptionKeySet As AeccPointDescriptionKeySet
    On Error Resume Next
    ' 创建一个新的描述码集合
    g_oDocument.PointDescriptionKeySets.Remove "Sample key Set"
    Set oPointDescriptionKeySet = g_oDocument.PointDescriptionKeySets.Add("Sample key Set")
    On Error GoTo 0
    If (oPointDescriptionKeySet Is Nothing) Then
        On Error Resume Next
        '  如果描述码集合被使用，则不能被移除，新的也不能创建，这种情况下使用已有的
        Set oPointDescriptionKeySet = g_oDocument.PointDescriptionKeySets.Item("Sample key Set")
        On Error GoTo 0
        If (oPointDescriptionKeySet Is Nothing) Then
            CreatePointDescriptionKey = False
            Exit Function
        End If
    End If
    ' 在集合中创建一个新的码值' 匹配任何以"SAMP"开头的描述
    Dim oPointDescriptionKey As AeccPointDescriptionKey
    On Error Resume Next
    '
    oPointDescriptionKeySet.Remove "SAMP*"
    Set oPointDescriptionKey = oPointDescriptionKeySet.Add("SAMP*")
    On Error GoTo 0
    If (oPointDescriptionKey Is Nothing) Then
        On Error Resume Next
        ' 如果码值被使用，则不能被移除，新的也不能创建，这种情况下使用已有的
        Set oPointDescriptionKey = oPointDescriptionKeySet.Item("SAMP*")
        On Error GoTo 0
        If (oPointDescriptionKey Is Nothing) Then
            CreatePointDescriptionKey = False
            Exit Function
        End If
    End If
    
    
    oPointDescriptionKey.Format = "SAMPLE"
    oPointDescriptionKey.OverrideLayer = False
    
    ' 为描述码指定样式和标签
    oPointDescriptionKey.OverridePointLabelStyle = True
    oPointDescriptionKey.PointLabelStyle = oLabelStyle.Name
    oPointDescriptionKey.OverridePointStyle = True
    oPointDescriptionKey.PointStyle = oPointStyle.Name
    
    oPointDescriptionKey.OverrideScaleParameter = True
    oPointDescriptionKey.OverrideFixedScaleFactor = False
    oPointDescriptionKey.UseDrawingScale = False
    oPointDescriptionKey.ScaleParameter = 1
    oPointDescriptionKey.ScaleXY = True
    
    oPointDescriptionKey.OverrideFixedRotation = True
    oPointDescriptionKey.FixedRotation = 0.785398163 ' 半径
    oPointDescriptionKey.ClockwiseRotation = True
    
    CreatePointDescriptionKey = True
End Function ' CreatePointDescriptionKey



''---------------------------------------------------------
'
'功能：创建并使用点组
'
'作者：
'
'
'日期：２００７/０8
'
'
'修改记录：无
'
'
''-----------------------------------------------------------
'
Public Function CreatePointGroup() As Boolean
    ' Make some point object for us to perform tests on.
    Dim oPoint1 As AeccPoint
    Dim oPoint2 As AeccPoint
    Dim oPoint3 As AeccPoint
    On Error Resume Next
    Set oPoint1 = g_oDocument.Points.Item(0)
    Set oPoint2 = g_oDocument.Points.Item(1)
    Set oPoint3 = g_oDocument.Points.Item(2)
    On Error GoTo 0
    If (oPoint3 Is Nothing) Then
        CreatePointGroup = False
        Exit Function
    End If

    ' 从文档中获取所有点编组的选择集.
    Dim oPointGroups As AeccPointGroups
    Set oPointGroups = g_oDocument.PointGroups
    If (oPointGroups Is Nothing) Then
        CreatePointGroup = False
        Exit Function
    End If
    
    ' 添加一个编组到集合中
    On Error Resume Next
    
    Set g_oPointGroup = oPointGroups.Item("Point_Group_01")
    On Error GoTo 0
    If (g_oPointGroup Is Nothing) Then
        Set g_oPointGroup = oPointGroups.Add("Point_Group_01")
    End If

    ' 使用QueryBuilder将点对象放置于任一个点编组中
    ' 向点编组中添加点1和点2
    g_oPointGroup.QueryBuilder.IncludeNames = "point1,point2"
    ' 用编号向点编组中添加点3
    g_oPointGroup.QueryBuilder.IncludeNumbers = oPoint3.Number
    ' 可以使用通配符，下面的代码将选择所有名称以"poi"开头的点.
    g_oPointGroup.QueryBuilder.IncludeNames = "poi*"
    ' 排除高程大于300的点
    g_oPointGroup.QueryBuilder.ExcludeElevations = ">300"
    ' 包含ID编号在100-200之间的点，还有206
    g_oPointGroup.QueryBuilder.IncludeNumbers = "100-200,206"
    
    '将编组中的所有点的高程设为100
    g_oPointGroup.Elevation = 100
    g_oPointGroup.OverrideElevation = True
    
    ' 点编组能够用于定义或者修改三角网（TIN）曲面
    On Error Resume Next
    Dim oSurf As AeccSurface
    Set oSurf = g_oDocument.Surfaces.Item(0)
    On Error GoTo 0
    If (oSurf Is Nothing) Then
        CreatePointGroup = False
        Exit Function
    End If
    
    If (oSurf.Type = aecckTinSurface) Then
        Dim oTinSurf As AeccTinSurface
        Set oTinSurf = oSurf
        oTinSurf.Update
        oTinSurf.PointGroups.Add g_oPointGroup
    Else
        CreatePointGroup = False
        Exit Function
    End If

    CreatePointGroup = True
End Function



''---------------------------------------------------------
'
'功能：导入点文件
'
'作者：
'
'
'日期：２００７/０8
'
'
'修改记录：无
'
'
''-----------------------------------------------------------
Public Function LoadPointsFromText() As Boolean
    Dim oPoints As AeccPoints
    Dim oImportOptions As New AeccPointImportOptions
    Dim sFileName As String
    Dim sFileFormat As String
    Dim iCount As Integer
    
    Set oPoints = g_oDocument.Points
    sFileName = g_oCivilApp.Path & "\Sample\Civil 3D API\Vba\SurfacePoints\Sample Point File.txt"
    'sFileName = g_oCivilApp.Path & "c:\Civil 3D \CH03\Sample Point File.txt"
    
    sFileFormat = "PENZ (space delimited)"
    oImportOptions.PointDuplicateResolution = aeccPointDuplicateOverwrite
    iCount = oPoints.ImportPoints(sFileName, sFileFormat, oImportOptions)
    If (iCount = 0) Then
        MsgBox "导入点文件失败."
        LoadPointsFromText = False
        Exit Function
    End If

    ' 输出点
    Dim oExportOptions As New AeccPointExportOptions
    'sFileName = g_oCivilApp.Path & "c:\Civil 3D \CH03\SamplePointFileOut.txt"
    sFileName = g_oCivilApp.Path & "\Sample\Civil 3D API\Vba\SurfacePoints\SamplePointFileOut.txt"
    
    oExportOptions.ExpandCoordinateData = True
    oPoints.ExportPoints sFileName, "PENZ (space delimited)", oExportOptions
    
    LoadPointsFromText = True
End Function

Attribute VB_Name = "Subroutines"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit




''---------------------------------------------------------
'
'功能：测试点和点组
'
'作者：
'
'
'日期：２００７/０8
'
'
'修改记录：无
'
'
''-----------------------------------------------------------Description Key.
'
Sub AddPoints()
    ' 获取程序对象
    If (GetBaseCivilObjects() = False) Then
        MsgBox "获取程序对象失败"
        Exit Sub
    End If
    
    
    If (CreatePointDescriptionKey() = False) Then
        Debug.Print "创建点描述码失败"
        Exit Sub
    End If
    
    If (CreatePoints() = False) Then
        Debug.Print "创建点失败."
        Exit Sub
    End If
    
    If (CreatePointGroup() = False) Then
        Debug.Print "创建点组失败."
        Exit Sub
    End If
End Sub



''---------------------------------------------------------
'
'功能：导入和导出点文件
'
'作者： Qin H.X.
'
'
'日期：２００７/０8
'
'
'修改记录：无
'
'
''-----------------------------------------------------------
'
Sub LoadPointsFromFile()
    ' Always get the objects again since MDI is supported.
    If (GetBaseCivilObjects() = False) Then
        Exit Sub
    End If
    
    If (LoadPointsFromText() = False) Then
        MsgBox "Error trying to load points from TXT file."
        Exit Sub
    End If
    Call EnumExistingPoints
End Sub
