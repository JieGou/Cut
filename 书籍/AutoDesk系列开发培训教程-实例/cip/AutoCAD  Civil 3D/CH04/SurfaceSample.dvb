Attribute VB_Name = "BaseObjects"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit

' 声明全局的程序、文档和数据库对象
Public g_oCivilApp As AeccApplication
Public g_oDocument As AeccDocument
Public g_oAeccDb As AeccDatabase


''---------------------------------------------------------
'
'功能：获取模块的程序、文档和数据库对象
'
'作者：
'
'
'日期：２００７/０8
'
'
'修改记录：无
'
'
''-----------------------------------------------------------
Public Function GetBaseCivilObjects() As Boolean
    Dim oApp As AcadApplication
    Set oApp = ThisDrawing.Application
    '需要指定版本号（5.0）.
    Const sAppName = "AeccXUiLand.AeccApplication.5.0"
    Set g_oCivilApp = oApp.GetInterfaceObject(sAppName)
    If g_oCivilApp Is Nothing Then
        MsgBox "获取程序对象 " & sAppName & "错误, 退出."
        GetBaseCivilObjects = False
        Exit Function
    End If
    Set g_oDocument = g_oCivilApp.ActiveDocument
    Set g_oAeccDb = g_oDocument.Database
    GetBaseCivilObjects = True
End Function

Attribute VB_Name = "Subroutines"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit




''---------------------------------------------------------
'
'功能：通过点文件创建曲面
'
'作者：
'
'
'日期：２００７/０8
'
'
'修改记录：无
'
'
''-----------------------------------------------------------
'
Sub CreateSurfaceFromFile()
    ' 获取程序对象.
    If (GetBaseCivilObjects() = False) Then
        Exit Sub
    End If
    
    If (CreateSurfaceByImportTXT() = False) Then
        MsgBox "通过点文件创建曲面失败."
        Exit Sub
    End If

    Call EnumExistingSurfaces
End Sub

''---------------------------------------------------------
'
'功能：创建曲面及其相关特性
'
'作者：
'
'
'日期：２００７/０8
'
'
'修改记录：无
'
'
''-----------------------------------------------------------
'
Public Sub RunSurfaceExample()

  ' 获取程序对象
    If (GetBaseCivilObjects() = False) Then
        MsgBox "获取程序对象失败."
        Exit Sub
    End If
    
    ' Create a surface to perform a check on.
    Dim oTinSurface As AeccTinSurface
    Set oTinSurface = CreateSurface()
    If (oTinSurface Is Nothing) Then
        MsgBox "创建面失败."
        Exit Sub
    End If
    
    ' 创建曲面高程分析
    Dim oSurfaceAnalysisElevation As AeccSurfaceAnalysisElevation
    Set oSurfaceAnalysisElevation = oTinSurface.SurfaceAnalysis.ElevationAnalysis
    Dim oElevationRegions As AeccElevationRegions
    '
    Dim dRegions As Long
    Dim dAsk As Long
    Dim dCount As Long
    dRegions = 11 '
    dAsk = dRegions
    Do
        Set oElevationRegions = oSurfaceAnalysisElevation.CalculateElevationRegions(dAsk, False)
        Debug.Print oSurfaceAnalysisElevation.ElevationRegions.Count
        dAsk = dAsk + 1
    Loop Until oSurfaceAnalysisElevation.ElevationRegions.Count = dRegions
    
    oElevationRegions.Item(0).color = 255
    oElevationRegions.Item(1).color = 254
    oElevationRegions.Item(2).color = 253
    oElevationRegions.Item(3).color = 252
    oElevationRegions.Item(4).color = 251
    oElevationRegions.Item(5).color = 250
    oElevationRegions.Item(6).color = 90
    oElevationRegions.Item(7).color = 92
    oElevationRegions.Item(8).color = 94
    oElevationRegions.Item(9).color = 96
    oElevationRegions.Item(10).color = 98

    '调整某个区域的范围
    oElevationRegions.Item(5).MaximumElevation = oElevationRegions.Item(5).MaximumElevation - 2.1
    oElevationRegions.Item(6).MinimumElevation = oElevationRegions.Item(6).MinimumElevation + 2.1
    '确保区域可见.
    oTinSurface.Style.ElevationStyle.DisplayStyle2d.Visible = True
    oTinSurface.Style.ElevationStyle.DisplayStyle3d.Visible = True
End Sub

Attribute VB_Name = "SurfaceStyle"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


''---------------------------------------------------------
'
'功能：创建曲面样式
'
'作者：
'
'
'日期：２００７/０8
'
'
'修改记录：无
'
'
''-----------------------------------------------------------
Public Function CreateSurfaceStyle(sStyleName As String) As Boolean
    Dim oSurfaceStyle As AeccSurfaceStyle
    Dim oSurfaceStyles As AeccSurfaceStyles
    Set oSurfaceStyles = g_oDocument.SurfaceStyles
    
    ' 创面面样式
    On Error Resume Next
    Set oSurfaceStyle = oSurfaceStyles.Item(sStyleName)
    On Error GoTo 0
    If (oSurfaceStyle Is Nothing) Then
        Set oSurfaceStyle = oSurfaceStyles.Add(sStyleName)
    End If

    ' 设置面样式
    oSurfaceStyle.ContourStyle.SmoothContours = True
    oSurfaceStyle.ContourStyle.SmoothingFactor = 10
    oSurfaceStyle.ContourStyle.SmoothingType = aeccAddVerticies
    oSurfaceStyle.ContourStyle.MinorContourDisplayStyle2d.Visible = True
    oSurfaceStyle.ContourStyle.MajorContourDisplayStyle3d.Visible = True
    oSurfaceStyle.ContourStyle.MinorContourDisplayStyle2d.Visible = True
    oSurfaceStyle.ContourStyle.MinorContourDisplayStyle3d.Visible = True
    oSurfaceStyle.ContourStyle.MinorContourInterval = 0.5
    oSurfaceStyle.ContourStyle.MajorContourColorScheme = "Greens"
    oSurfaceStyle.ContourStyle.MinorContourColorScheme = "Land"
    oSurfaceStyle.ContourStyle.UseColorScheme = True
    oSurfaceStyle.ContourStyle.MajorContourDisplayStyle2d.color = 43
    oSurfaceStyle.ContourStyle.MajorContourDisplayStyle3d.color = 43
    oSurfaceStyle.ContourStyle.MinorContourDisplayStyle2d.color = 47
    oSurfaceStyle.ContourStyle.MinorContourDisplayStyle3d.color = 47
    oSurfaceStyle.TriangleStyle.DisplayStyle2d.Visible = False
    oSurfaceStyle.TriangleStyle.DisplayStyle3d.Visible = False
    oSurfaceStyle.BoundaryStyle.DisplayStyle2d.Visible = True
    oSurfaceStyle.BoundaryStyle.DisplayStyle3d.Visible = True
    oSurfaceStyle.BoundaryStyle.DisplayStyle2d.color = 40
    oSurfaceStyle.BoundaryStyle.DisplayStyle3d.color = 40
    oSurfaceStyle.PointStyle.DisplayStyle2d.Visible = True
    oSurfaceStyle.PointStyle.DisplayStyle3d.Visible = True
    oSurfaceStyle.PointStyle.DisplayStyle2d.color = 20
    oSurfaceStyle.PointStyle.DisplayStyle3d.color = 20
    oSurfaceStyle.PointStyle.DataPointsDisplayType = 0
    
    CreateSurfaceStyle = True
End Function


'
' Set display style to only display points along the exterior boundaries.
'
Public Function DisplayBorderPointsOnly() As Boolean
    Dim bRetVal As Boolean
    bRetVal = SetSurfaceDisplay(True, False, True, False, False, False, False, False, False, False, False, False)
    DisplayBorderPointsOnly = bRetVal
End Function

'
' Set display style to display TIN exterior boundaries and triangles in 2D and 3D
'
Public Function DisplayBorderTrianglesOnly() As Boolean
    Dim bRetVal As Boolean
    bRetVal = SetSurfaceDisplay(False, True, True, False, False, False, False, False, False, False, False, False)
    DisplayBorderTrianglesOnly = bRetVal
End Function

'
' Set display style to display only major and minor contours.
'
Public Function DisplayBorderMajorMinorContoursOnly() As Boolean
    Dim bRetVal As Boolean
    bRetVal = SetSurfaceDisplay(False, False, True, True, True, False, False, False, False, False, False, False)
    DisplayBorderMajorMinorContoursOnly = bRetVal
End Function

'
' Set display style to display only the border and grid of a grid surface.
'
Public Function DisplayBorderGridedOnly() As Boolean
    Dim bRetVal As Boolean
    bRetVal = SetSurfaceDisplay(False, False, True, False, False, False, True, False, False, False, False, False)
    DisplayBorderGridedOnly = bRetVal
End Function

'
' Set display style to display only the border and triangle slopes.
'
Public Function DisplayBorderSlopesOnly() As Boolean
    Dim bRetVal As Boolean
    bRetVal = SetSurfaceDisplay(False, False, True, False, False, False, False, False, False, True, False, False)
    DisplayBorderSlopesOnly = bRetVal
End Function

'
' Set display style to display only the border and slope indicators.
'
Public Function DisplayBorderSlopeArrowsOnly() As Boolean
    Dim bRetVal As Boolean
    bRetVal = SetSurfaceDisplay(False, False, True, False, False, False, False, False, False, False, True, False)
    DisplayBorderSlopeArrowsOnly = bRetVal
End Function

'
' Set display style to display only the border and watershed indicators.
'
Public Function DisplayBorderWatershedsOnly() As Boolean
    Dim bRetVal As Boolean
    bRetVal = SetSurfaceDisplay(False, False, True, False, False, False, False, False, False, False, False, True)
    DisplayBorderWatershedsOnly = bRetVal
End Function

'
' Set display style to display only the border.
'
Public Function DisplayBorderOnly() As Boolean
    Dim bRetVal As Boolean
    bRetVal = SetSurfaceDisplay(False, False, True, False, False, False, False, False, False, False, False, False)
    DisplayBorderOnly = bRetVal
End Function

''---------------------------------------------------------
'
'功能：Set Surface Display
'
'作者：
'
'
'日期：２００７/０8
'
'
'修改记录：无
'
'
''-----------------------------------------------------------
'
Public Function SetSurfaceDisplay(bPoints As Boolean, bTriangles As Boolean, bBorder As Boolean, _
    bMajorContour As Boolean, bMinorContour As Boolean, bUserContour As Boolean, _
    bGrided As Boolean, bDirections As Boolean, bElevations As Boolean, _
    bSlopes As Boolean, bSlopeArrows As Boolean, bWaterSheds As Boolean) As Boolean
    
    Dim oSurfaceStyle As AeccSurfaceStyle
    On Error Resume Next
    Set oSurfaceStyle = g_oDocument.SurfaceStyles.Item("Elevations")
    On Error GoTo 0
    If (oSurfaceStyle Is Nothing) Then
        On Error Resume Next
        Set oSurfaceStyle = g_oDocument.SurfaceStyles.Item("Standard")
        On Error GoTo 0
        If (oSurfaceStyle Is Nothing) Then
            Set oSurfaceStyle = g_oDocument.SurfaceStyles.Item(0)
        End If
    End If
    
    oSurfaceStyle.PointStyle.DisplayStyle2d.Visible = bPoints
    oSurfaceStyle.PointStyle.DisplayStyle3d.Visible = bPoints
    
    oSurfaceStyle.TriangleStyle.DisplayStyle2d.Visible = bTriangles
    oSurfaceStyle.TriangleStyle.DisplayStyle3d.Visible = bTriangles
    
    oSurfaceStyle.BoundaryStyle.DisplayExteriorBoundaries = bBorder
    oSurfaceStyle.BoundaryStyle.DisplayInteriorBoundaries = False
    
    oSurfaceStyle.BoundaryStyle.DisplayStyle2d.Visible = bBorder
    oSurfaceStyle.BoundaryStyle.DisplayStyle3d.Visible = bBorder
    
    oSurfaceStyle.ContourStyle.MajorContourDisplayStyle2d.Visible = bMajorContour
    oSurfaceStyle.ContourStyle.MajorContourDisplayStyle3d.Visible = bMajorContour
    
    oSurfaceStyle.ContourStyle.MinorContourDisplayStyle2d.Visible = bMinorContour
    oSurfaceStyle.ContourStyle.MinorContourDisplayStyle3d.Visible = bMinorContour
    
    oSurfaceStyle.ContourStyle.UserContourDisplayStyle2d.Visible = bUserContour
    oSurfaceStyle.ContourStyle.UserContourDisplayStyle3d.Visible = bUserContour
    
    oSurfaceStyle.GridStyle.DisplayStyle2d.Visible = bGrided
    oSurfaceStyle.GridStyle.DisplayStyle3d.Visible = bGrided
    
    oSurfaceStyle.DirectionStyle.DisplayStyle2d.Visible = bDirections
    oSurfaceStyle.DirectionStyle.DisplayStyle3d.Visible = bDirections
    
    oSurfaceStyle.ElevationStyle.DisplayStyle2d.Visible = bElevations
    oSurfaceStyle.ElevationStyle.DisplayStyle3d.Visible = bElevations
    
    oSurfaceStyle.SlopeStyle.DisplayStyle2d.Visible = bSlopes
    oSurfaceStyle.SlopeStyle.DisplayStyle3d.Visible = bSlopes
    
    oSurfaceStyle.SlopeArrowStyle.DisplayStyle2d.Visible = bSlopeArrows
    oSurfaceStyle.SlopeArrowStyle.DisplayStyle3d.Visible = bSlopeArrows
    
    oSurfaceStyle.WatershedStyle.DisplayStyle2d.Visible = bWaterSheds
    oSurfaceStyle.WatershedStyle.DisplayStyle3d.Visible = bWaterSheds
    
    ThisDrawing.Application.Update
    SetSurfaceDisplay = True
End Function

''---------------------------------------------------------
'
'功能：创建点样式
'
'作者：
'
'
'日期：２００７/０8
'
'
'修改记录：无
'
'
''-----------------------------------------------------------
'
Public Function CreatePointStyle(sStyleName As String) As Boolean
    Dim oPointStyle As AeccPointStyle
    Dim oPointStyles As AeccPointStyles
    Set oPointStyles = g_oDocument.PointStyles
    
    '
    On Error Resume Next
    Set oPointStyle = oPointStyles.Item(sStyleName)
    ' 创建点样式对象.
    On Error GoTo 0
    If (oPointStyle Is Nothing) Then
        Set oPointStyle = oPointStyles.Add(sStyleName)
    End If

    '  设置所创建点样式对象的属性
    oPointStyle.MarkerType = aeccUseCustomMarker
    oPointStyle.CustomMarkerStyle = aeccCustomMarkerDot
    oPointStyle.CustomMarkerSuperimposeStyle = aeccCustomMarkerSuperimposeCircle

    CreatePointStyle = True
End Function


''---------------------------------------------------------
'
'功能：创建标签样式
'
'作者：
'
'
'日期：２００７/０8
'
'
'修改记录：无
'
'
''-----------------------------------------------------------
Public Function CreateLabelStyle(oLabelStyle As AeccLabelStyle) As Boolean
    Dim oLabelStyleTickComponent As AeccLabelStyleTickComponent
    Dim oLabelStyleBlockComponent As AeccLabelStyleBlockComponent
    Dim oLabelStyleLineComponent As AeccLabelStyleLineComponent
    Dim oLabelStyleTextComponent As AeccLabelStyleTextComponent

    '
    On Error Resume Next
    '以添加记号组件
    oLabelStyle.TickComponents.Remove "New Tick"
    Set oLabelStyleTickComponent = oLabelStyle.TickComponents.Item("New Tick")
    On Error GoTo 0
    If (oLabelStyleTickComponent Is Nothing) Then
        Set oLabelStyleTickComponent = oLabelStyle.TickComponents.Add("New Tick")
    End If

    oLabelStyleTickComponent.Lineweight.Value = 60 ' .60 mm
    oLabelStyleTickComponent.AlignWithObject = True ' perpendicular to alignment
    oLabelStyleTickComponent.Angle = 0# ' in radians
    oLabelStyleTickComponent.Visibility = True

    ' 向标签样式添加块组件
    On Error Resume Next
    oLabelStyle.BlockComponents.Remove "New Block"
    Set oLabelStyleBlockComponent = oLabelStyle.BlockComponents.Item("New Block")
    On Error GoTo 0
    If (oLabelStyleBlockComponent Is Nothing) Then
        Set oLabelStyleBlockComponent = oLabelStyle.BlockComponents.Add("New Block")
    End If
    'oLabelStyleBlockComponent.BlockName = "AeccTickCircle"
    oLabelStyleBlockComponent.Visibility = True
    
    ' 向标签样式添加直线组件
    On Error Resume Next
    oLabelStyle.LineComponents.Remove "New Line"
    Set oLabelStyleLineComponent = oLabelStyle.LineComponents.Item("New Line")
    On Error GoTo 0
    If (oLabelStyleLineComponent Is Nothing) Then
        Set oLabelStyleLineComponent = oLabelStyle.LineComponents.Add("New Line")
    End If
    oLabelStyleLineComponent.color = 40 ' orange-yellow
    oLabelStyleLineComponent.Angle = 0.7854 ' 2.094 ' radians, = 120 degrees
    oLabelStyleLineComponent.Length = 0.015
    oLabelStyleLineComponent.StartPointXOffset = 0.005
    oLabelStyleLineComponent.StartPointYOffset = 0.005
    oLabelStyleLineComponent.Visibility = True

    '向标签添加文本组件
    Set oLabelStyleTextComponent = oLabelStyle.TextComponents.Item(0)

    oLabelStyleTextComponent.AllowToCurve = True
    oLabelStyleTextComponent.XOffset = -0.01
    oLabelStyleTextComponent.YOffset = 0.008
    oLabelStyleTextComponent.Contents = "N<[Point Number]>"
    oLabelStyleTextComponent.color = 253
    CreateLabelStyle = True
End Function

Attribute VB_Name = "Surfaces"

'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


''---------------------------------------------------------
'
'功能：加载XML来修改曲面
'
'作者：
'
'
'日期：２００７/０8
'
'
'修改记录：无
'
'
''-----------------------------------------------------------
'
Public Function CreateSurfaceByImportXML() As Boolean
    Dim oSurfaces As AeccSurfaces
    Set oSurfaces = g_oDocument.Surfaces
    
    ' 获取已经存在的"EG"面, 然后加载XML 文件
    Dim oSurface As AeccSurface
    Dim sXmlFileName As String
    On Error Resume Next
    Set oSurface = oSurfaces.Item("EG")
    On Error GoTo 0
    
    If (oSurface Is Nothing) Then
        'sXmlFileName = "c:\\Civil 3D API\EG.xml"
        sXmlFileName = Application.Path & "\Sample\Civil 3D API\Vba\SurfacePoints\EG.xml"
        Set oSurface = oSurfaces.ImportXML(sXmlFileName)
        If (oSurface Is Nothing) Then
            Debug.Print "加载XML 文件: " & Err.Description
            CreateSurfaceByImportXML = False
            Err.Clear
        End If
    End If
    
    '
    ThisDrawing.Application.ZoomExtents
    Call DisplayBorderTrianglesOnly
    
    CreateSurfaceByImportXML = True
End Function



''---------------------------------------------------------
'
'功能：通过点文件创建面
'
'作者：
'
'
'日期：２００７/０8
'
'
'修改记录：无
'
'
''-----------------------------------------------------------
Public Function CreateSurfaceByImportTXT() As Boolean
    Dim oSurfaces As AeccSurfaces
    Set oSurfaces = g_oDocument.Surfaces
    
    '
    Dim oSurface As AeccSurface
    Dim oTinSurface As AeccTinSurface
    On Error Resume Next
    Set oSurface = oSurfaces.Item("EG")
    On Error GoTo 0
    If (oSurface Is Nothing) Then
        Dim oTinCreationData As New AeccTinCreationData
        oTinCreationData.Name = "EG"
        oTinCreationData.Description = "TIN Surface from TXT file"
        oTinCreationData.Layer = g_oDocument.Layers.Item(0).Name
        oTinCreationData.BaseLayer = g_oDocument.Layers.Item(0).Name
        If (CreateSurfaceStyle("SURFACE_STYLE_01") = False) Then
            CreateSurfaceByImportTXT = False
            Exit Function
        End If
        oTinCreationData.Style = "SURFACE_STYLE_01"
        Set oTinSurface = oSurfaces.AddTinSurface(oTinCreationData)
    Else
        Set oTinSurface = oSurface
    End If
    
    ' 通过导入点文件构造面
    Dim sFileName As String
    sFileName = InputBox("选择要导入的点文件", "Surface Sample", "C:\Civil 3D API\Sample Point File.txt")
    oTinSurface.PointFiles.Add sFileName
    If Err.Number <> 0 Then
        MsgBox "导入点文件失败"
        CreateSurfaceByImportTXT = False
        Exit Function
    End If
    
    
    ThisDrawing.Application.ZoomExtents
    Call DisplayBorderMajorMinorContoursOnly
    
    CreateSurfaceByImportTXT = True
End Function
 
''---------------------------------------------------------
'
'功能：遍历所有的曲面
'
'作者：
'
'
'日期：２００７/０8
'
'
'修改记录：无
'
'
''-----------------------------------------------------------
Public Function EnumExistingSurfaces() As Boolean
    Dim oSurface As AeccSurface
    Dim i As Integer
    For i = 0 To g_oDocument.Surfaces.Count - 1
        Set oSurface = g_oDocument.Surfaces.Item(i)
        Select Case (oSurface.Type)
            Case aecckGridSurface:
                Dim oGridSurface As AeccGridSurface
                Set oGridSurface = oSurface
                Debug.Print oGridSurface.Name & " 栅格曲面 "
            Case aecckTinSurface:
                Dim oTinSurface As AeccTinSurface
                Set oTinSurface = oSurface
                Debug.Print oTinSurface.Name & " 三角网曲面 "
            Case aecckGridVolumeSurface:
                Dim oGridVolumeSurface As AeccGridVolumeSurface
                Set oGridVolumeSurface = oSurface
                Debug.Print oGridVolumeSurface.Name & " 栅格体量曲面"
            Case aecckTinVolumeSurface:
                Dim oTinVolumeSurface As AeccTinVolumeSurface
                Set oTinVolumeSurface = oSurface
                Debug.Print oTinVolumeSurface.Name & " 三角网体量曲面 "
        End Select
    Next i
    
    EnumExistingSurfaces = True
End Function


''---------------------------------------------------------
'
'功能：添加一条等高线到TIN曲面
'
'作者：
'
'
'日期：２００７/０8
'
'
'修改记录：无
'
'
''-----------------------------------------------------------
Public Function AddTinSurfaceContour(oTinSurface As AeccTinSurface) As Boolean
    ' 添加一条等高线到TIN曲面
    Dim dContourPoints(0 To 8) As Double
    Dim o3DPoly As Acad3DPolyline
  ' 定义3个点坐标
    dContourPoints(0) = 2500: dContourPoints(1) = 1500: dContourPoints(2) = 100
    dContourPoints(3) = 2600: dContourPoints(4) = 1600: dContourPoints(5) = 100
    ' 即使将第三个点的Z值设为50，这对等高线的高程也是没有任何影响的
    ' 它将仍然按照第一点的高程100来定位这条等高线
    dContourPoints(6) = 2400: dContourPoints(7) = 1600: dContourPoints(8) = 50
    Set o3DPoly = g_oDocument.Database.ModelSpace.Add3DPoly(dContourPoints)
    o3DPoly.Closed = True
    Dim oEntities(0) As AcadEntity
    Set oEntities(0) = o3DPoly
    'g_oDocument.Database.ModelSpace.Delete
    Dim oNewContour As AeccSurfaceContour
    Set oNewContour = oTinSurface.Contours.Add(oEntities, "Sample Contour", 55#, 0.0698, 63#, 1#) ' 0.0698 rad = 4 deg


End Function

''---------------------------------------------------------
'
'功能：通过点组修改TIN曲面
'
'作者：
'
'
'日期：２００７/０8
'
'
'修改记录：无
'
'
''-----------------------------------------------------------

Private Function CreateSurfacebyPointGroup(oTinSurface As AeccTinSurface)
    Const MAX_X As Double = 5000
    Const MAX_Y As Double = 5000

    '添加30个点到文档的点集合中
    Dim i As Integer
    Dim oPoints As AeccPoints
    Set oPoints = g_oDocument.Points
    Dim dDifference As Double
    dDifference = 1000# - 800#
    For i = 0 To 30
        Dim pt(0 To 2) As Double
        pt(0) = Int(MAX_X * Rnd())
        pt(1) = Int(MAX_Y * Rnd())
        pt(2) = Int(dDifference * Rnd()) + 800#
        Dim oPoint As AeccPoint
        Set oPoint = oPoints.Add(pt)
        ' .
        oPoint.Name = oTinSurface.Name & "Point" & CStr(i)
    Next i

    ' 获取点组集合
    Dim oPtGroups As AeccPointGroups
    Dim oPtGroup As AeccPointGroup
    Set oPtGroups = g_oDocument.PointGroups
    If (oPtGroups Is Nothing) Then
        CreateSurfacebyPointGroup = False
        Exit Function
    End If

    ' 创建点组
    On Error Resume Next ' if we try to get an item that does not exist, we get an error.
    Set oPtGroup = oPtGroups.Item("POINT_GROUP_01" & oTinSurface.Name)
    On Error GoTo 0
    If (oPtGroup Is Nothing) Then
        Set oPtGroup = oPtGroups.Add("POINT_GROUP_01" & oTinSurface.Name)
    End If

    ' 添加随机产生的点到点组，所有的点的名称都将以"Point"开头
    oPtGroup.QueryBuilder.IncludeNames = oTinSurface.Name & "Point" & "*"
    
    ' Check to see if things are working alright.
    If (oPtGroup.PointCount = 0) Then
        MsgBox "No points in point group"
        CreateSurfacebyPointGroup = False
        Exit Function
    End If

    ' 使用点编组来TIN 面.
    oTinSurface.PointGroups.Add oPtGroup
    oTinSurface.Update

    CreateSurfacebyPointGroup = True
End Function '



''---------------------------------------------------------
'
'功能：创建曲面及其相关特性
'
'作者：
'
'
'日期：２００７/０8
'
'
'修改记录：无
'
'
''-----------------------------------------------------------
Public Function CreateSurface() As AeccTinSurface
    '
    If (g_oDocument Is Nothing) Then
        Set CreateSurface = Nothing
        Exit Function
    End If

    Dim oSurfaces As AeccSurfaces
    '获取曲面的集合
    Set oSurfaces = g_oDocument.Surfaces
    Dim oSurface As AeccSurface
    
    Dim sDemFileName As String
    ' If we try to get an item that does not exist, we get an error.
    On Error Resume Next
    oSurfaces.Remove "Surface_Ground_01"
    Set oSurface = oSurfaces.Item("Surface_Ground_01")
    On Error GoTo 0
    If (oSurface Is Nothing) Then
        ' 创建面
        Dim oTinSurface As AeccTinSurface
        Dim oTinCreationData As New AeccTinCreationData
        
        oTinCreationData.BaseLayer = g_oDocument.Layers.Item(0).Name
        oTinCreationData.Layer = g_oDocument.Layers.Item(0).Name
        oTinCreationData.Description = ""
        oTinCreationData.Name = "Surface_Ground_01"
        If (CreateSurfaceStyle("SURFACE_STYLE_01") = False) Then
            Exit Function
        End If
        oTinCreationData.Style = "SURFACE_STYLE_01"
        Set oTinSurface = g_oDocument.Surfaces.AddTinSurface(oTinCreationData)
        If (oTinSurface Is Nothing) Then
            MsgBox "创建面失败 "
            Set CreateSurface = Nothing
            Exit Function
        End If

        ' Add random points to our surface.
        Call CreateSurfacebyPointGroup(oTinSurface)

        ' 创建一条标准特征线
        Dim o3DPoly As Acad3DPolyline
        Dim dPoints(0 To 11) As Double

        '
        dPoints(0) = 1200: dPoints(1) = 1200: dPoints(2) = 300
        dPoints(3) = 2000: dPoints(4) = 3000: dPoints(5) = 300
        dPoints(6) = 3000: dPoints(7) = 2000: dPoints(8) = 300
        dPoints(9) = 3800: dPoints(10) = 3800: dPoints(11) = 300

        Set o3DPoly = Nothing
        Set o3DPoly = g_oDocument.Database.ModelSpace.Add3DPoly(dPoints)
        o3DPoly.Closed = False

        Dim oBreakline As AeccSurfaceBreakline
        Dim oEntityArray(0) As AcadEntity
        Set oEntityArray(0) = o3DPoly
        Set oBreakline = oTinSurface.Breaklines.AddStandardBreakline(oEntityArray, "Standard Breakline_01", 1#)

        ' 添加陡壁特征线
        dPoints(0) = 2700: dPoints(1) = 1200: dPoints(2) = 300
        dPoints(3) = 3500: dPoints(4) = 1500: dPoints(5) = 300
        dPoints(6) = 3750: dPoints(7) = 1800: dPoints(8) = 300
        dPoints(9) = 3900: dPoints(10) = 3000: dPoints(11) = 300
        Set o3DPoly = Nothing
        Set o3DPoly = g_oDocument.Database.ModelSpace.Add3DPoly(dPoints)
        o3DPoly.Closed = False
        '
        Dim vElevations(0) As Variant
        '
        Dim dElevations(3) As Double
        Dim bOffsets(0) As Boolean
        
        dElevations(0) = 30#: dElevations(1) = 90#: dElevations(2) = 90#: dElevations(3) = 40#
        vElevations(0) = dElevations
        bOffsets(0) = True
        Set oBreakline = Nothing
        Set oEntityArray(0) = Nothing
        Set oEntityArray(0) = o3DPoly
        
        Set oBreakline = oTinSurface.Breaklines.AddWallBreakline(oEntityArray, "Sample Wall Break", 1#, vElevations, bOffsets)
        
        Call AddTinSurfaceContour(oTinSurface)

        '向曲面添加一个外部边界
        Dim oPoly As AcadPolyline
        dPoints(0) = 1000: dPoints(1) = 1000: dPoints(2) = 0
        dPoints(3) = 1000: dPoints(4) = 4000: dPoints(5) = 0
        dPoints(6) = 4000: dPoints(7) = 4000: dPoints(8) = 0
        dPoints(9) = 4000: dPoints(10) = 1000: dPoints(11) = 0

        Set oPoly = g_oDocument.Database.ModelSpace.AddPolyline(dPoints)
        oPoly.Closed = True

        ' 这里的第三个参数描述了如何处理其内部的三角形（这里是"外部"）
        ' 如果需要设置虚特征线边界，则将第四个参数赋为True；否则反之
        ' 最后一个参数即为中点垂距值
        Dim oNewBoundary As AeccSurfaceBoundary
        Set oNewBoundary = oTinSurface.Boundaries.Add(oPoly, "Sample Boundary", aeccBoundaryOuter, True, 10#)
        g_oCivilApp.Update

        ThisDrawing.Application.ZoomExtents

        Set CreateSurface = oTinSurface
    Else
        '
        Set CreateSurface = oSurface
    End If

End Function
