Attribute VB_Name = "BaseObjects"
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


' 声明全局的程序、文档和数据库对象
Public g_oCivilApp As AeccRoadwayApplication
Public g_oRoadwayDocument As AeccRoadwayDocument
Public g_oRoadwayDatabase As AeccRoadwayDatabase



''---------------------------------------------------------
'
'功能：获取模块的程序、文档和数据库对象
'
'作者：
'
'
'日期：２００７/０8
'
'
'修改记录：无
'
'
''-----------------------------------------------------------
Function GetCorridorObjects() As Boolean
    Dim oApp As AcadApplication
    Set oApp = ThisDrawing.Application
    ' 需要指定版本号（5.0）
    Const sAppName = "AeccXUiRoadway.AeccRoadwayApplication.5.0"
    Set g_oCivilApp = oApp.GetInterfaceObject(sAppName)
    If (g_oCivilApp Is Nothing) Then
        MsgBox "创建程序失败 " & sAppName & ", 退出."
        GetCorridorObjects = False
        Exit Function
    End If
    Set g_oRoadwayDocument = g_oCivilApp.ActiveDocument
    Set g_oRoadwayDatabase = g_oRoadwayDocument.Database
    GetCorridorObjects = True
End Function

Attribute VB_Name = "Corridor"

' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


''---------------------------------------------------------
'
'功能：基于路线、纵断面和装配创建道路
'
'作者：
'
'
'日期：２００７/０8
'
'
'修改记录：无
'
'
''-----------------------------------------------------------
Public Function CreateCorridor() As Boolean

    ' 创建道路需要通基于路线、纵断面和装配
    ' 创建简单的路线对象
    ' '无站点路线是Civil 3D 2008 新增的内容，2007下需要创建站点下的路线

    Dim oAlignments As AeccAlignmentsSiteless
    Set oAlignments = g_oRoadwayDocument.AlignmentsSiteless
    Dim oAlignment As AeccAlignment
    On Error Resume Next
    Set oAlignment = oAlignments.Item("ALIGNMENT_01")
    On Error GoTo 0
    If (oAlignment Is Nothing) Then
        '设定样式
        Dim sStyleName As String
        Dim sLabelSetName As String
        sStyleName = g_oRoadwayDocument.AlignmentStyles.Item(0).Name
        sLabelSetName = g_oRoadwayDocument.AlignmentLabelStyleSets.Item(0).Name
        
        '
        Set oAlignment = oAlignments.Add("ALIGNMENT_01", "0", sStyleName, sLabelSetName)
        If (oAlignment Is Nothing) Then
             ThisDrawing.Utility.Prompt ("创建简单的路线对象失败: " & Err.Description & vbCrLf)
            Err.Clear
            ThisDrawing.Application.ZoomExtents
            CreateCorridor = False
            Exit Function
        End If
    
        ' 添加路线的几何实体
        Dim dPoint1(0 To 2) As Double
        Dim dPoint2(0 To 2) As Double
        Dim dRadius As Double
        Dim dLength As Double
        dPoint1(0) = 4932.4: dPoint1(1) = 4784.2: dPoint1(2) = 0
        dPoint2(0) = 5600.2: dPoint2(1) = 5550.9: dPoint2(2) = 0
        dRadius = 751.8
        dLength = 999.9
        
        Dim oAlignmentArc As AeccAlignmentArc
        Set oAlignmentArc = oAlignment.Entities.AddFixedCurve6(dPoint1, dPoint2, 751.8, True)
        Dim oAlignmentTangent As AeccAlignmentTangent
        Set oAlignmentTangent = oAlignment.Entities.AddFloatingLine2(oAlignmentArc.Id, dLength)
    End If


    ' 基于路线创建纵断面
    Dim oProfiles As AeccProfiles
    On Error Resume Next
    Set oProfiles = oAlignment.Profiles
    On Error GoTo 0
    If (oProfiles Is Nothing) Then
         ThisDrawing.Utility.Prompt ("获取纵断面失败" & vbCrLf)
        CreateCorridor = False
        Exit Function
    End If

    Dim oProfile As AeccProfile
    On Error Resume Next
    Set oProfile = oProfiles.Item("PROFILE_01")
    On Error GoTo 0
    If (oProfile Is Nothing) Then
        ' Get the default profile style.
        Dim sProfileStyleName As String
        sProfileStyleName = g_oRoadwayDocument.LandProfileStyles.Item(0).Name

        Set oProfile = oProfiles.Add("PROFILE_01", aeccFinishedGround, sProfileStyleName, oAlignment.StartingStation, oAlignment.EndingStation, "0")

        Dim dLoc1(0 To 1) As Double
        Dim dLoc2(0 To 1) As Double
        Dim oProfileTangent1 As aeccProfileTangent
        dLoc1(0) = oAlignment.StartingStation: dLoc1(1) = 0#
        dLoc2(0) = 758.2: dLoc2(1) = 4.37
        Set oProfileTangent1 = oProfile.Entities.AddFixedTangent(dLoc1, dLoc2)
        Dim oProfileTangent2 As aeccProfileTangent
        dLoc1(0) = 1208.2: dLoc1(1) = 12.55
        dLoc2(0) = oAlignment.EndingStation: dLoc2(1) = -10#
        Set oProfileTangent2 = oProfile.Entities.AddFixedTangent(dLoc1, dLoc2)
        
        Dim dCrestLen As Double
        dCrestLen = 1208.2 - 758.2
        Call oProfile.Entities.AddFreeSymmetricParabolaByLength(oProfileTangent1.Id, oProfileTangent2.Id, aeccCrest, dCrestLen, True)

        oProfile.Update
    End If


    ' 获取装配
    
    Dim oAssemblies As AeccAssemblies
    On Error Resume Next
    Set oAssemblies = g_oRoadwayDocument.Assemblies
    On Error GoTo 0
    If (oAssemblies Is Nothing) Then
        MsgBox "获取装配失败"
        CreateCorridor = False
        Exit Function
    End If

    '获取装配集合的第一个装配
    Dim oAssembly As AeccAssembly
    On Error Resume Next
    Set oAssembly = oAssemblies.Item(0)
    On Error GoTo 0
    If (oAssembly Is Nothing) Then
        MsgBox "该例子需要文档中存在已创建的装配"
        CreateCorridor = False
        Exit Function
    End If

    
    ' 创建道路
    
    Dim oCorridors As AeccCorridors
    On Error Resume Next
    Set oCorridors = g_oRoadwayDatabase.Corridors
    On Error GoTo 0

    Dim oCorridor As AeccCorridor
    Set oCorridor = oCorridors.Add("CORRIDOR_01", oAlignment.Name, oProfile.Name, oAssembly.Name)
    
    ''''''''''''''''''''''''''''''''''''''''''''''''''''''
    ' 说明：只是创建了一个简单的道路，
    ' 还需要用户在工具面板内重建(Rebuild)
    ' 才能在当前图形中看到所创建的路线
    ''''''''''''''''''''''''''''''''''''''''''''''''''''''
       
    CreateCorridor = True
End Function



'''---------------------------------------------------------
'
'功能：基于路线、纵断面和装配创建道路
'
'作者：
'
'
'日期：２００７/０8
'
'
'修改记录：无
'
'
''-----------------------------------------------------------
Public Function ListAssembliesToWord() As Boolean
    '
    If (oPara Is Nothing) Then
        ListAssembliesToWord = False
        Exit Function
    End If

    ' Get a reference to the assemblies collection.
    Dim oAssemblies As AeccAssemblies
    On Error Resume Next
    Set oAssemblies = g_oRoadwayDocument.Assemblies
    On Error GoTo 0
    If (oAssemblies Is Nothing) Then
        MsgBox "There are no assemblies in this document."
        ListAssembliesToWord = False
        Exit Function
    End If
    
    ' Add the title to Word.
    ThisDrawing.Utility.Prompt ("Number of Assemblies: " & oAssemblies.Count & vbCrLf)
    oPara.Range.Font.Bold = True
    oPara.Range.Font.Size = 14
    oPara.Range.Font.Name = "Courier New"
    oPara.Format.SpaceAfter = 24    '24 pt spacing after paragraph.
     
   
    oPara.Range.Font.Bold = False
    oPara.Range.Font.Size = 10
    oPara.Format.SpaceAfter = 4
   
    ' Get the list of all assemblies in the current
    ' document.
    Dim oAssembly As AeccAssembly
    For Each oAssembly In oAssemblies
        ThisDrawing.Utility.Prompt ("Assembly: " & oAssembly.Name & vbCrLf)
         
        ThisDrawing.Utility.Prompt ("Display name: " & oAssembly.DisplayName & vbCrLf)
         
        ThisDrawing.Utility.Prompt ("Code set style: " & oAssembly.CodeSetStyleName & vbCrLf)
         
    Next
    
    ' Function completed successfully.
    ListAssembliesToWord = True
End Function ' ListAssembliesToWord



''---------------------------------------------------------
'
'功能：访问道路对象信息
'
'作者：
'
'
'日期：２００７/０8
'
'
'修改记录：无
'
'
''-----------------------------------------------------------
'
Public Function ListCorridors() As Boolean
    Dim X As Double
    Dim Y As Double
    Dim Z As Double

 
    Dim oCorridors As AeccCorridors
    
    On Error Resume Next
    Set oCorridors = g_oRoadwayDocument.Corridors
    On Error GoTo 0
    If (oCorridors Is Nothing) Then
        MsgBox "获取道路集合失败。"
        ListCorridors = False
        Exit Function
    End If
    
    Dim oCorridor As AeccCorridor
    For Each oCorridor In oCorridors
        ' 道路基准线
        Dim oBaseline As AeccBaseline
        For Each oBaseline In oCorridor.Baselines
             ThisDrawing.Utility.Prompt ("基准线路线名称: " & oBaseline.Alignment.Name & vbCrLf)
             ThisDrawing.Utility.Prompt ("基准线纵断面名称: " & oBaseline.profile.Name & vbCrLf)
             ThisDrawing.Utility.Prompt ("起始里程: " & oBaseline.StartStation & vbCrLf)
             ThisDrawing.Utility.Prompt ("结束里程: " & oBaseline.EndStation & vbCrLf)
            
            '列出所有的要素线集合和沿基准线的要素线
            Dim oBaselineFeatureLines As AeccBaselineFeatureLines
            Set oBaselineFeatureLines = oBaseline.MainBaselineFeatureLines
            
            Dim oFeatureLinesCol As AeccFeatureLinesCol
            Set oFeatureLinesCol = oBaselineFeatureLines.FeatureLinesCol
            
            Dim oFeatureLines As AeccFeatureLines
            For Each oFeatureLines In oFeatureLinesCol
                Dim sCodes As String
                sCodes = oFeatureLines.FeatureLineCodeInfo.CodeName
                ThisDrawing.Utility.Prompt ("要素线 :" & vbCrLf)
                ThisDrawing.Utility.Prompt ("要素线数目: " & oFeatureLines.Count & vbCrLf)
                
                Dim oFeatureLine As AeccFeatureLine
                For Each oFeatureLine In oFeatureLines
                    ThisDrawing.Utility.Prompt ("  要素线编码名称: " & oFeatureLine.CodeName & vbCrLf)
                    
                    ' 输出所有沿要素线的点
                    Dim oFeatureLinePoint As AeccFeatureLinePoint
                    For Each oFeatureLinePoint In oFeatureLine.FeatureLinePoints
                        X = oFeatureLinePoint.XYZ(0)
                        Y = oFeatureLinePoint.XYZ(1)
                        Z = oFeatureLinePoint.XYZ(2)
                       ThisDrawing.Utility.Prompt ("    点: " & X & ", " & Y & ", " & Z & vbCrLf)
                    
                    Next ' Points in a feature line
                Next ' Feature lines
            Next ' Collections of feature lines
            
            '获取道路基准线区域
            Dim oBaselineRegion As AeccBaselineRegion
            For Each oBaselineRegion In oBaseline.BaselineRegions
                
                ThisDrawing.Utility.Prompt ("基准线区域" & vbCrLf)
                ThisDrawing.Utility.Prompt ("开始里程: " & oBaselineRegion.StartStation & vbCrLf)
                ThisDrawing.Utility.Prompt ("结束里程: " & oBaselineRegion.EndStation & vbCrLf)
                
                ' 添加里程
                'oBaselineRegion.AddStation 1234.5, "Station description"
                'oBaselineRegion.DeleteStation 1234.5
                
                '  访问基准线区域的应用装配
                Dim oAppliedAssembly As AeccAppliedAssembly
                For Each oAppliedAssembly In oBaselineRegion.AppliedAssemblies
                    Dim lCount As Long
                    ThisDrawing.Utility.Prompt (" 应用装配" & vbCrLf)
                    lCount = oAppliedAssembly.GetLinks().Count
                    ThisDrawing.Utility.Prompt ("   链接数目: " & lCount & vbCrLf)
                    
                    lCount = oAppliedAssembly.GetPoints().Count
                    ThisDrawing.Utility.Prompt ("  点数目: " & lCount & vbCrLf)
                    
                    lCount = oAppliedAssembly.GetShapes().Count
                    ThisDrawing.Utility.Prompt ("  造型数目: " & lCount & vbCrLf)
                    
                Next ' Applied assemblies
                
                
                '获取一定基准线区域内的每条偏移基准线
                Dim oBaseBaseline As IAeccBaseBaseline
                For Each oBaseBaseline In oBaselineRegion.OffsetBaselines
                    Dim dMainStart As Double ' station on main baseline
                    Dim dMainEnd As Double ' station on main baseline
                    Dim vOE As Variant

                    Select Case oBaseline.Type
                        Case aeccCorridorOffsetBaseline
                            Dim oOffsetBaseline As AeccOffsetBaseline
                            Set oOffsetBaseline = oBaseBaseline
                            
                            ' 报告偏移基准线
                            dMainStart = oOffsetBaseline.StartStationOnMainBaseline
                            dMainEnd = oOffsetBaseline.EndStationOnMainBaseline
                            ThisDrawing.Utility.Prompt (" - 偏移基准线, 里程从 " & dMainStart & " 到 " & dMainEnd & vbCrLf)
                             
                            
                            ' 基准线起始里程的偏移量
                            vOE = oOffsetBaseline.GetOffsetElevationFromMainBaselineStation(dMainStart)
                            ThisDrawing.Utility.Prompt (" -  在开始里程位置被偏移: " & vOE(0) & " （水平方向） 和: " & vOE(1) & " （垂直方向）" & vbCrLf)
                             
                            vOE = oOffsetBaseline.GetOffsetElevationFromMainBaselineStation(dMainEnd)
                            ThisDrawing.Utility.Prompt (" - 在终点里程位置被偏移: " & vOE(0) & "（水平方向） 和: " & vOE(1) & " （垂直方向）" & vbCrLf)
                             
                        Case aeccCorridorHardcodedOffsetBaseline
                             
                            Dim oHardcodedOffsetBaseline As AeccHardcodedOffsetBaseline
                            Set oHardcodedOffsetBaseline = oBaseBaseline

                            '硬代码偏移基准线
                            dMainStart = oHardcodedOffsetBaseline.StartStation
                            dMainEnd = oHardcodedOffsetBaseline.EndStation
                            ThisDrawing.Utility.Prompt (" - 硬代码偏移基准线, 里程从" & dMainStart & "  到 " & dMainEnd & vbCrLf)

                            vOE = oHardcodedOffsetBaseline.OffsetElevationFromMainBaseline
                            ThisDrawing.Utility.Prompt (" - 位置被偏移: " & vOE(0) & " （水平方向） 和: " & vOE(1) & " （垂直方向）" & vbCrLf)
                             
                           
                            'Dim oBaselineFeatureLines As AeccBaselineFeatureLines
                            'oBaselineFeatureLines = oHardcodedOffsetBaseline.RelatedOffsetBaselineFeatureLines
                            '
                    End Select
                Next ' Offset baselines
            Next ' Baseline regions
        Next ' Baselines

        
        ''''''''''''''''''''''''''''''''''''''''''''''''''
        
        '访问道路的所有道路曲面信息和使用的点代码
        
        Dim oCorridorSurface As AeccCorridorSurface
        For Each oCorridorSurface In oCorridor.CorridorSurfaces
            ThisDrawing.Utility.Prompt ("道路曲面: " & oCorridorSurface.Name & vbCrLf)
            Dim dElev As Double
            'dElev = oCorridorSurface.FindElevationAtXY(4400.5, 4000.7)
            'ThisDrawing.Utility.Prompt ("点（ 4400.5, 4000.7）到高程为: " & dElev & vbCrLf)

            ' 获取要素线、链接和点代码
            Dim sCodeArray() As String
            Dim sCodeList As String
            sCodeArray = oCorridorSurface.FeatureLineCodes
            Dim i As Integer
            
            For i = 0 To UBound(sCodeArray)
                sCodeList = sCodeList & " " & sCodeArray(i)
            Next i
            ThisDrawing.Utility.Prompt ("要素线代码: " & sCodeList & vbCrLf)
            
            sCodeArray = oCorridorSurface.LinkCodes
            For i = 0 To UBound(sCodeArray)
                sCodeList = sCodeList & " " & sCodeArray(i)
            Next i
            ThisDrawing.Utility.Prompt ("链接代码: " & sCodeList & vbCrLf)
             
            
            sCodeArray = oCorridorSurface.PointCodes
            For i = 0 To UBound(sCodeArray)
                sCodeList = sCodeList & " " & sCodeArray(i)
            Next i
            ThisDrawing.Utility.Prompt ("点代码: " & sCodeList & vbCrLf)
            


            '访问道路边界
                Dim vPoints As Variant
                Dim oCorridorSurfaceBoundary As AeccCorridorSurfaceBoundary
            For Each oCorridorSurfaceBoundary In oCorridorSurface.Boundaries
                Dim sBoundaryTitle As String
                If (oCorridorSurfaceBoundary.Type = aeccCorridorSurfaceInsideBoundary) Then
                    sBoundaryTitle = "  内边界: "
                Else
                    sBoundaryTitle = "  外边界: "
                End If
                ThisDrawing.Utility.Prompt (sBoundaryTitle & oCorridorSurfaceBoundary.Name & vbCrLf)
                 
                vPoints = oCorridorSurfaceBoundary.GetPolygonPoints()
                ThisDrawing.Utility.Prompt ("    " & UBound(vPoints) & " points" & vbCrLf)
                


                '输出边界的所有点的位置
                For i = 0 To UBound(vPoints)
                    X = vPoints(i)(0)
                    Y = vPoints(i)(1)
                    Z = vPoints(i)(2)
                    ThisDrawing.Utility.Prompt ("    点 " & i & ": " & X & ", " & Y & ", " & Z & vbCrLf)
                Next i

                ' 访问边界的要素组件
                ThisDrawing.Utility.Prompt ("  要素组件" & vbCrLf)
                ThisDrawing.Utility.Prompt ("    数目: " & oCorridorSurfaceBoundary.FeatureLineComponents.Count & vbCrLf)
                 Dim oFeatureLineComponent As AeccFeatureLineComponent
                For Each oFeatureLineComponent In oCorridorSurfaceBoundary.FeatureLineComponents
                    ThisDrawing.Utility.Prompt ("    代码: " & oFeatureLineComponent.FeatureLine.CodeName & vbCrLf)
                    ThisDrawing.Utility.Prompt ("    起始里程: " & oFeatureLineComponent.StartStation & vbCrLf)
                    ThisDrawing.Utility.Prompt ("    结束里程: " & oFeatureLineComponent.EndStation & vbCrLf)
                    ThisDrawing.Utility.Prompt ("    是否用户开始里程: " & CStr(oFeatureLineComponent.UseStartStation) & vbCrLf)
                    ThisDrawing.Utility.Prompt ("    是否用户结束里程: " & CStr(oFeatureLineComponent.UseEndStation) & vbCrLf)
                Next ' Feature line components
            Next ' Corridor surface boundaries
            
            ' 访问道路遮罩
            Dim oCorridorSurfaceMask As AeccCorridorSurfaceMask
            For Each oCorridorSurfaceMask In oCorridorSurface.Masks
                ThisDrawing.Utility.Prompt ("  遮罩: " & oCorridorSurfaceMask.Name & vbCrLf)
                
                vPoints = oCorridorSurfaceMask.GetPolygonPoints()
                ThisDrawing.Utility.Prompt ("    " & UBound(vPoints) & " 点" & vbCrLf)
                ' 输出遮罩的所有点的位置

                For i = 0 To UBound(vPoints) '  & ", " &
                    X = vPoints(i)(0)
                    Y = vPoints(i)(1)
                    Z = vPoints(i)(2)
                    ThisDrawing.Utility.Prompt ("    Point " & i & ": " & X & ", " & Y & ", " & Z & vbCrLf)
                
                Next i
                ' 访问遮罩的要素组件
                ThisDrawing.Utility.Prompt ("  要素组件" & vbCrLf)
                 
                ThisDrawing.Utility.Prompt ("    数目: " & oCorridorSurfaceMask.FeatureLineComponents.Count & vbCrLf)
                 
                For Each oFeatureLineComponent In oCorridorSurfaceMask.FeatureLineComponents
                    ThisDrawing.Utility.Prompt ("    代码: " & oFeatureLineComponent.FeatureLine.CodeName & vbCrLf)
                    ThisDrawing.Utility.Prompt ("    起始里程: " & oFeatureLineComponent.StartStation & vbCrLf)
                    ThisDrawing.Utility.Prompt ("    结束里程: " & oFeatureLineComponent.EndStation & vbCrLf)
                    ThisDrawing.Utility.Prompt ("    是否用户开始里程: " & oFeatureLineComponent.UseStartStation & vbCrLf)
                    ThisDrawing.Utility.Prompt ("    是否用户结束里程: " & oFeatureLineComponent.UseEndStation & vbCrLf)
                Next ' Feature line components
            Next ' Corridor surface masks
        Next ' oCorridorSurface
        
    Next ' Corridors
    
    Close #1
    
    ' Function completed successfully.
    ListCorridors = True
End Function ' ListCorridors


'
''---------------------------------------------------------
'
'功能：访问应用装配信息
'
'作者：
'
'
'日期：２００７/０8
'
'
'修改记录：无
'
'
''-----------------------------------------------------------
Public Function DisplaySubassemblyInfo(oAppliedSubassembly As AeccAppliedSubassembly)

    Dim S, O, E As Double
    With oAppliedSubassembly
        S = .OriginStationOffsetElevationToBaseline(0)
        O = .OriginStationOffsetElevationToBaseline(1)
        E = .OriginStationOffsetElevationToBaseline(2)
    End With
    
    ThisDrawing.Utility.Prompt ("  到基准线的里程: " & S & vbCrLf)
    ThisDrawing.Utility.Prompt ("  到基准线的平移距离: " & O & vbCrLf)
    ThisDrawing.Utility.Prompt ("  到基准线的高程: " & E & vbCrLf)
     
    
    ' 获取部件(Subassembly)原型信息
    Dim oSubassembly As AeccSubassembly
    Set oSubassembly = oAppliedSubassembly.SubassemblyDbEntity
    Dim sSubInfo As String
    sSubInfo = oSubassembly.Name
    ThisDrawing.Utility.Prompt ("  部件名称: " & sSubInfo & vbCrLf)
    DisplaySubassemblyInfo = True
End Function



Public Function CreateVolumeSurface() As Boolean
    ' 获取图形中得曲面
    Dim oSurfaces As AeccSurfaces
    Set oSurfaces = g_oRoadwayDocument.Surfaces

    ' 构造体积曲面
    Dim oTinVolumeCreationData As New AeccTinVolumeCreationData
    oTinVolumeCreationData.Name = "VOLUME_SURFACE_NAME"
    oTinVolumeCreationData.BaseLayer = g_oRoadwayDocument.Layers.Item(0).Name
    oTinVolumeCreationData.Layer = g_oRoadwayDocument.Layers.Item(0).Name
    Set oTinVolumeCreationData.BaseSurface = oSurfaces.Item("EG")
    Set oTinVolumeCreationData.ComparisonSurface = oSurfaces.Item("Corridor_1")
    oTinVolumeCreationData.Style = oSurfaces.Item("EG").StyleName
    oTinVolumeCreationData.Description = "道路的体积曲面"
    
    ' 创建体积曲面（基准曲面EG和道路曲面）
    Dim oTinVolumeSurface As AeccTinVolumeSurface
    On Error Resume Next
    Set oTinVolumeSurface = oSurfaces.AddTinVolumeSurface(oTinVolumeCreationData)
    On Error GoTo 0
    If (oTinVolumeSurface Is Nothing) Then
        MsgBox "创建体积曲面失败"
        CreateVolumeSurface = False
        Exit Function
    End If
    
    ' 获取体积曲面的数据
    Dim dNetVol As Double
    Dim dCutVol As Double
    Dim dFillVol As Double
    dNetVol = oTinVolumeSurface.Statistics.NetVolume
    dCutVol = oTinVolumeSurface.Statistics.CutVolume
    dFillVol = oTinVolumeSurface.Statistics.FillVolume
    MsgBox "净土方 = " & dNetVol & " cu.m" & _
      vbNewLine & "挖方 = " & dCutVol & " cu.m" & _
      vbNewLine & "填方 = " & dFillVol & " cu.m", _
      vbOKOnly, _
      "在曲面 """ & _
      oTinVolumeCreationData.BaseSurface.Name & _
      """ 和 """ & _
      oTinVolumeCreationData.ComparisonSurface.Name & _
      "相差的体积"""
    
    CreateVolumeSurface = True
End Function ' CreateVolumeSurface


'
''---------------------------------------------------------
'
'功能：创建装配和道路样式
'
'作者：
'
'
'日期：２００７/０8
'
'
'修改记录：无
'
'
''-----------------------------------------------------------
Public Function CreateStyles() As Boolean
    ' 创建装配和道路样式
    Dim oAssemblyStyle As AeccAssemblyStyle
    Set oAssemblyStyle = g_oRoadwayDocument.AssemblyStyles.Add(ASSEMBLY_STYLE_NAME)
    With oAssemblyStyle.MarkerStyleAtMainBaseline
        .CustomMarkerStyle = aeccCustomMarkerX
        .MarkerDisplayStyle2d.color = 10 ' red
        .MarkerDisplayStyle2d.Visible = True
    End With
    
    '
    Dim oShapeStyle As AeccRoadwayShapeStyle
    Set oShapeStyle = g_oRoadwayDocument.ShapeStyles.Add(SHAPE_STYLE_NAME)
    With oShapeStyle
        .AreaFillDisplayStyle2d.color = 50 ' yellow
        .AreaFillDisplayStyle2d.Visible = True
        .AreaFillHatchDisplayStyle2d.HatchType = aeccHatchPreDefined
        .AreaFillHatchDisplayStyle2d.Pattern = "LINE"
        .BorderDisplayStyle2d.color = 30 ' orange
        .BorderDisplayStyle2d.Visible = True
    End With
    
    '
    Dim oLinkStyle As AeccRoadwayLinkStyle
    Set oLinkStyle = g_oRoadwayDocument.LinkStyles.Add(LINK_STYLE_NAME)
    With oLinkStyle
        .LinkDisplayStyle2d.color = 80
        .LinkDisplayStyle2d.Visible = True
    End With
    
    '
    Dim oStyleSet As AeccRoadwayStyleSet
    Set oStyleSet = g_oRoadwayDocument.StyleSets.Add(STYLE_SET_NAME)
    Call oStyleSet.Add( _
        aeccLinkType, _
        "TOP", _
        g_oRoadwayDocument.LinkStyles.Item(LINK_STYLE_NAME))
    Call oStyleSet.Add( _
        aeccShapeType, _
        "BASE", _
        g_oRoadwayDocument.ShapeStyles.Item(SHAPE_STYLE_NAME))
    
    '
    oStyleSet.InitAsCurrent
    
End Function

Attribute VB_Name = "Globals"

' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit


Global Const VOLUME_SURFACE_NAME As String = "Corridor Volume"
Global Const ALIGNMENT_NAME As String = "Alignment 01"
Global Const PROFILE_NAME As String = "Profile 01"
Global Const CORRIDOR_NAME As String = "Corridor 01"

Global Const ASSEMBLY_STYLE_NAME As String = "New Style 01"
Global Const SHAPE_STYLE_NAME As String = "Shape Style 01"
Global Const LINK_STYLE_NAME As String = "Link Style 01"
Global Const STYLE_SET_NAME As String = "Style Set 01"

Attribute VB_Name = "Subroutines"
'
' Copyright {2007} by Autodesk, Inc.
'
' Permission to use, copy, modify, and distribute this software for
' any purpose and without fee is hereby granted, provided that the
' above copyright notice appears in all copies and  that both that
' copyright notice and the limited warranty and  restricted rights
' notice below appear in all supporting  documentation.
'
' AUTODESK PROVIDES THIS PROGRAM "AS IS" AND WITH ALL FAULTS.
' AUTODESK SPECIFICALLY DISCLAIMS ANY IMPLIED WARRANTY OF
' MERCHANTABILITY OR FITNESS FOR A PARTICULAR USE. AUTODESK, INC.
' DOES NOT WARRANT THAT THE OPERATION OF THE PROGRAM WILL BE
' UNINTERRUPTED OR ERROR FREE.
'
' Use, duplication, or disclosure by the U.S. Government is subject to
' restrictions set forth in FAR 52.227-19 (Commercial Computer
' Software - Restricted Rights) and DFAR 252.227-7013(c)(1)(ii)
' (Rights in Technical Data and Computer Software), as applicable.
'
'
'
Option Explicit
'




''---------------------------------------------------------
'
'功能：基于路线、纵断面和装配创建一个新的道路
'
'作者：
'
'
'日期：２００７/０8
'
'
'修改记录：无
'
'
''-----------------------------------------------------------

Sub CreateCorridorExample()
    If ThisDrawing.Name <> "CH09_corridors_0.dwg" Then
        MsgBox "请打开CH09_corridors_0.dwg后重新运行"
        Exit Sub
    
    End If
    '获取程序对象
    If (GetCorridorObjects = False) Then
        Exit Sub
    End If
    
    ' 基于路线、纵断面和装配创建一个新的道路
    If (CreateCorridor() = False) Then
        Exit Sub
    End If
    
End Sub



''---------------------------------------------------------
'
'功能：获取道路信息
'
'作者：
'
'
'日期：２００７/０8
'
'
'修改记录：无
'
'
''-----------------------------------------------------------

Sub GetCorridorInfoExample()

    If ThisDrawing.Name <> "CH09_corridors.dwg" Then
        MsgBox "请打开CH09_corridors.dwg后重新运行"
        Exit Sub
    
    End If
    '获取程序对象
    If (GetCorridorObjects = False) Then
        Exit Sub
    End If
    
   
    ' 显示道路信息
    If (ListCorridors() = False) Then
        Exit Sub
    End If
    
    '计算体积
    Call CreateVolumeSurface
    
    g_oCivilApp.Update
End Sub
